FME workspace 5_traitement_calculs_statistiques.fmw

Parameters:
- SourceDataset_POSTGIS = portail_gdb   # Connection
- SourceDataset_POSTGRES = portail_gdb   # Connection
- DestDataset_XLSXW_9 = C:\Users\mathi\Documents\MDT\TM\statistiques\statistiques_deplacements.xlsx   # Destination Microsoft Excel File
- DestDataset_XLSXW = C:\Users\mathi\Documents\MDT\TM\statistiques\statistiques_profils.xlsx   # Destination Microsoft Excel File
- SourceDataset_XLSXR = $(FME_MF_DIR)distance_et_temps_parcours.xlsx   # Source Microsoft Excel File(s)
- DestDataset_XLSXW_6 = C:\Users\mathi\Documents\MDT\TM\statistiques\statistiques_deplacements_km.xlsx   # Destination Microsoft Excel File

Readers:
- POSTGIS_1: POSTGIS from $(SourceDataset_POSTGIS)
- POSTGRES_1: POSTGRES from $(SourceDataset_POSTGRES)
- XLSXR_2: XLSXR from $(SourceDataset_XLSXR)

Writers:
- XLSXW_2: XLSXW to $(DestDataset_XLSXW_9)
- XLSXW_1: XLSXW to $(DestDataset_XLSXW)
- XLSXW_4: XLSXW to $(DestDataset_XLSXW_6)

FeatureMerger_16
    ATTR_ACCUM_MODE = Merge Supplier
    ATTR_CONFLICT_RES = Use Requestor
    IGNORE_NULLS = No
    JOIN_KEYS = @Value(id) @Value(utilisateur_id) AUTO
    MERGE_TYPE = Attributes Only
    PROCESS_DUPS = NO
    REJECT_NULL_MISSING_KEYS = No
    SUPPLIERS_FIRST = No
    MERGED -> FeatureMerger_Deplacements-utilisateurs [SUPPLIER]
    MERGED -> FeatureMerger_Deplacements-profils [SUPPLIER]
    MERGED -> FeatureMerger_21 [REQUESTOR]
    MERGED -> FeatureMerger_54 [SUPPLIER]
    MERGED -> FeatureMerger_55 [SUPPLIER]
    MERGED -> FeatureMerger_57 [SUPPLIER]
    MERGED -> FeatureMerger_58 [SUPPLIER]
    MERGED -> Junction_19
    MERGED -> Junction_21
    MERGED -> Junction_23
    MERGED -> Junction_25
    UNMERGED_REQUESTOR -> FeatureMerger_Deplacements-utilisateurs [SUPPLIER]
FeatureMerger_Deplacements-utilisateurs
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    MERGED -> Tester_Motif_defini_D-T_4
    MERGED -> Tester_Motif_defini_Pro
    MERGED -> Tester_Motif_defini_D-T
    MERGED -> Tester_Motif_defini_Pro_4
    MERGED -> Tester_Velo_Velo-TP_Semaine_1
    MERGED -> Tester_Velo_Velo-TP_Semaine_2
    MERGED -> Junction_15
Note: FeatureMerger_45 : Requestor
Junction_15
    -> Junction_16
Note: FeatureMerger_Deplacements-utilisateurs : Merged
Junction_16
    -> FeatureMerger_45 [REQUESTOR]
FeatureMerger_Deplacements-profils
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    MERGED -> Tester_Motif_defini_D-T_2
    MERGED -> Tester_Motif_defini_Pro_2
    MERGED -> Tester_Motif_defini_D-T_3
    MERGED -> Tester_Motif_defini_Pro_3
    MERGED -> Junction_27
Note: FeatureMerger_44 : Requestor
Junction_27
    -> Junction_28
Note: FeatureMerger_Deplacements-profils : Merged
Junction_28
    -> FeatureMerger_44 [REQUESTOR]
Note: FeatureMerger_64 : Supplier
Junction_19
    -> Junction_20
Note: FeatureMerger_63 : Supplier
Junction_21
    -> Junction_22
Note: FeatureMerger_61 : Supplier
Junction_25
    -> Junction_26
Note: FeatureMerger_60 : Supplier
Junction_23
    -> Junction_24
FeatureMerger_21
    ATTR_ACCUM_MODE = Merge Supplier
    ATTR_CONFLICT_RES = Use Requestor
    IGNORE_NULLS = No
    JOIN_KEYS = @Value(utilisateur_id) @Value(utilisateur_id) AUTO
    MERGE_TYPE = Attributes Only
    PROCESS_DUPS = NO
    REJECT_NULL_MISSING_KEYS = No
    SUPPLIERS_FIRST = No
    MERGED -> StatisticsCalculator_Profil_par_societe
    MERGED -> StatisticsCalculator_Profil_par_site
    MERGED -> StatisticsCalculator_Profil_par_fonction
    MERGED -> StatisticsCalculator_Profil_par_taux
    MERGED -> StatisticsCalculator_Profil_par_teletravail
    MERGED -> StatisticsCalculator_Profil_par_PMR
    MERGED -> StatisticsCalculator_Profil_par_Bike_to_work
    MERGED -> StatisticsCalculator_7
    UNMERGED_REQUESTOR -> StatisticsCalculator_8
    UNUSED_SUPPLIER -> StatisticsCalculator_9
voiture (reader XLSXR_2)
    attributes: id_deplacement number(5,0), distance_voiture_km number(7,2), temps_parcours_voiture_min number(4,0)
    -> FeatureMerger_48 [REQUESTOR]
velo (reader XLSXR_2)
    attributes: id_deplacement number(5,0), distance_velo_km number(6,2), temps_parcours_velo_min number(4,0)
    -> FeatureMerger_48 [SUPPLIER]
FeatureMerger_48
    ATTR_ACCUM_MODE = Merge Supplier
    ATTR_CONFLICT_RES = Use Requestor
    IGNORE_NULLS = No
    JOIN_KEYS = @Value(id_deplacement) @Value(id_deplacement) AUTO
    MERGE_TYPE = Attributes Only
    PROCESS_DUPS = NO
    REJECT_NULL_MISSING_KEYS = No
    SUPPLIERS_FIRST = No
    MERGED -> FeatureMerger_49 [REQUESTOR]
marche (reader XLSXR_2)
    attributes: id_deplacement number(5,0), distance_marche_km number(6,2), temps_parcours_marche_min number(5,0)
    -> FeatureMerger_49 [SUPPLIER]
FeatureMerger_49
    ATTR_ACCUM_MODE = Merge Supplier
    ATTR_CONFLICT_RES = Use Requestor
    IGNORE_NULLS = No
    JOIN_KEYS = @Value(id_deplacement) @Value(id_deplacement) AUTO
    MERGE_TYPE = Attributes Only
    PROCESS_DUPS = NO
    REJECT_NULL_MISSING_KEYS = No
    SUPPLIERS_FIRST = No
    MERGED -> FeatureMerger_44 [SUPPLIER]
    MERGED -> FeatureMerger_45 [SUPPLIER]
FeatureMerger_45
    ATTR_ACCUM_MODE = Merge Supplier
    ATTR_CONFLICT_RES = Use Requestor
    IGNORE_NULLS = No
    JOIN_KEYS = @Value(id_deplacement) @Value(id_deplacement) AUTO
    MERGE_TYPE = Attributes Only
    PROCESS_DUPS = NO
    REJECT_NULL_MISSING_KEYS = No
    SUPPLIERS_FIRST = No
    MERGED -> Tester_Motif_defini_D-T_5
    MERGED -> Tester_Motif_defini_Pro_5
FeatureMerger_44
    ATTR_ACCUM_MODE = Merge Supplier
    ATTR_CONFLICT_RES = Use Requestor
    IGNORE_NULLS = No
    JOIN_KEYS = @Value(id_deplacement) @Value(id_deplacement) AUTO
    MERGE_TYPE = Attributes Only
    PROCESS_DUPS = NO
    REJECT_NULL_MISSING_KEYS = No
    SUPPLIERS_FIRST = No
    MERGED -> Tester_Motif_defini_D-T_6
    MERGED -> Tester_Motif_defini_Pro_6
    MERGED -> Tester_Motif_defini_D-T_7
    MERGED -> Tester_Motif_defini_Pro_7

Bookmark: Gestion des clés étrangères des déplacements
deplacements_deplacement (reader POSTGRES_1)
    attributes: id_deplacement serial,PrimaryKey, date date, heure_depart time, heure_arrivee time, lieu_arrivee_id int4,BTREE, lieu_depart_id int4,BTREE, mode_id int4,BTREE, motif_id int4,BTREE, raison_id int4,BTREE, utilisateur_id int4,BTREE
    -> FeatureMerger_6 [REQUESTOR]
deplacements_mode (reader POSTGRES_1)
    attributes: id_mode serial,PrimaryKey, nom_mode varchar(100), alias_mode varchar(100)
    -> FeatureMerger_6 [SUPPLIER]
    -> Junction
    -> Junction_3
    -> Junction_5
    -> Junction_7
FeatureMerger_6
    ATTR_ACCUM_MODE = Merge Supplier
    ATTR_CONFLICT_RES = Use Requestor
    IGNORE_NULLS = No
    JOIN_KEYS = @Value(mode_id) @Value(id_mode) AUTO
    MERGE_TYPE = Attributes Only
    PROCESS_DUPS = NO
    REJECT_NULL_MISSING_KEYS = No
    SUPPLIERS_FIRST = No
    MERGED -> FeatureMerger_7 [REQUESTOR]
Note: FeatureMerger_17 : Requestor
Junction
    -> Junction_2
Note: FeatureMerger_19 : Requestor
Junction_3
    -> Junction_4
Note: FeatureMerger_29 : Requestor
Junction_5
    -> Junction_6
Note: FeatureMerger_28 : Requestor
Junction_7
    -> Junction_8
deplacements_motif (reader POSTGRES_1)
    attributes: id_motif serial,PrimaryKey, nom_motif varchar(150), alias_motif varchar(100)
    -> FeatureMerger_7 [SUPPLIER]
FeatureMerger_7
    ATTR_ACCUM_MODE = Merge Supplier
    ATTR_CONFLICT_RES = Use Requestor
    IGNORE_NULLS = No
    JOIN_KEYS = @Value(motif_id) @Value(id_motif) AUTO
    MERGE_TYPE = Attributes Only
    PROCESS_DUPS = NO
    REJECT_NULL_MISSING_KEYS = No
    SUPPLIERS_FIRST = No
    MERGED -> FeatureMerger_8 [REQUESTOR]
deplacements_raison (reader POSTGRES_1)
    attributes: id_raison serial,PrimaryKey, nom_raison varchar(100), alias_raison varchar(100)
    -> FeatureMerger_8 [SUPPLIER]
FeatureMerger_8
    ATTR_ACCUM_MODE = Merge Supplier
    ATTR_CONFLICT_RES = Use Requestor
    IGNORE_NULLS = No
    JOIN_KEYS = @Value(raison_id) @Value(id_raison) AUTO
    MERGE_TYPE = Attributes Only
    PROCESS_DUPS = NO
    REJECT_NULL_MISSING_KEYS = No
    SUPPLIERS_FIRST = No
    MERGED -> AttributeManager_14
AttributeManager_14
    ATTR_TABLE:
      REMOVE id_mode
      REMOVE id_motif
      REMOVE id_raison
    -> FeatureMerger_4 [REQUESTOR]
    -> FeatureMerger_21 [SUPPLIER]

Bookmark: Statistiques modes pour le Groupe, nombre de kilomètres
Note: public.deplacements_mode
Junction_2
    -> FeatureMerger_17 [REQUESTOR]
Tester_Motif_defini_D-T_5
    BOOL_OP = OR
    TEST_CLAUSE:
      TEST @Value(motif_defini_id) = 1
      TEST @Value(motif_defini_id) = 2
      TEST @Value(motif_defini_id) = 3
      TEST @Value(motif_defini_id) = 4
      TEST @Value(motif_defini_id) = 6
      TEST @Value(motif_defini_id) = 7
    TEST_MODE = TEST
    PASSED -> AttributeManager
AttributeManager
    ATTR_TABLE = SET_TO distance_km_pendulaire = FME_CONDITIONAL:DEFAULT_VALUE'@Value(distance_voiture_km)'BOOL_OP;OR;COMPOSITE_TEST;1 OR 2;TEST @Value(nom_mode) = Marche;TEST @Value(nom_mode) = Trottinette'@Value(distance_marche_km)'BOOL_OP;OR;COMPOSITE_TEST;1;TEST @Value(nom_mode) = Vélo, vélo électrique'@Value(distance_velo_km)'FME_NUM_CONDITIONS3___
    -> StatisticsCalculator_Mode_3
StatisticsCalculator_Mode_3
    CALCULATION_MODE = NUMERIC
    FEAT_STATS = distance_km_pendulaire,NUMERIC_MODE,,,,SUM,,,,,,,,,
    GROUP_BY = mode_id
    SUMMARY -> FeatureMerger_17 [SUPPLIER]
FeatureMerger_17
    ATTR_ACCUM_MODE = Merge Supplier
    ATTR_CONFLICT_RES = Use Requestor
    IGNORE_NULLS = No
    JOIN_KEYS = @Value(id_mode) @Value(mode_id) AUTO
    MERGE_TYPE = Attributes Only
    PROCESS_DUPS = NO
    REJECT_NULL_MISSING_KEYS = No
    SUPPLIERS_FIRST = No
    MERGED -> AttributeManager_6
    UNMERGED_REQUESTOR -> AttributeManager_6
AttributeManager_6
    ATTR_TABLE = RENAME_SET_VALUE distance_km_pendulaire.sum > nb_km_parcourus_pendulaires_groupe
    USER_EXPOSED_ATTRIBUTES = id_deplacement.total_count,distance_voiture_km.sum
    -> FeatureMerger_18 [REQUESTOR]
Tester_Motif_defini_Pro_5
    BOOL_OP = OR
    TEST_CLAUSE:
      TEST @Value(motif_defini_id) = 5
      TEST @Value(motif_defini_id) = 8
    TEST_MODE = TEST
    PASSED -> AttributeManager_12
AttributeManager_12
    ATTR_TABLE = SET_TO distance_km_pro = FME_CONDITIONAL:DEFAULT_VALUE'@Value(distance_voiture_km)'BOOL_OP;OR;COMPOSITE_TEST;1 OR 2;TEST @Value(nom_mode) = Marche;TEST @Value(nom_mode) = Trottinette'@Value(distance_marche_km)'BOOL_OP;OR;COMPOSITE_TEST;1;TEST @Value(nom_mode) = Vélo, vélo électrique'@Value(distance_velo_km)'FME_NUM_CONDITIONS3___
    -> StatisticsCalculator_Mode_4
StatisticsCalculator_Mode_4
    CALCULATION_MODE = NUMERIC
    FEAT_STATS = distance_km_pro,NUMERIC_MODE,,,,SUM,,,,,,,,,
    GROUP_BY = mode_id
    SUMMARY -> FeatureMerger_18 [SUPPLIER]
FeatureMerger_18
    ATTR_ACCUM_MODE = Merge Supplier
    ATTR_CONFLICT_RES = Use Requestor
    IGNORE_NULLS = No
    JOIN_KEYS = @Value(id_mode) @Value(mode_id) AUTO
    MERGE_TYPE = Attributes Only
    PROCESS_DUPS = NO
    REJECT_NULL_MISSING_KEYS = No
    SUPPLIERS_FIRST = No
    MERGED -> AttributeManager_7
    UNMERGED_REQUESTOR -> AttributeManager_7
AttributeManager_7
    ATTR_TABLE:
      SET_TO nb_km_parcourus_pendulaires_groupe = @Evaluate(@round(@Value(nb_km_parcourus_pendulaires_groupe),0))
      RENAME_SET_VALUE distance_km_pro.sum > nb_km_parcourus_pro_groupe = FME_CONDITIONAL:DEFAULT_VALUE'@Evaluate(@round(@Value(nb_km_parcourus_pro_groupe),0))'BOOL_OP;OR;COMPOSITE_TEST;1;TEST nb_km_parcourus_pro_groupe ATTRIBUTE_IS_MISSING _FME_BLANK_STRING_'0'FME_NUM_CONDITIONS2___
    USER_EXPOSED_ATTRIBUTES = id_deplacement.total_count,nb_depl_pendulaires_groupe
    -> Sorter_13
Sorter_13
    SORT_PARM = id_mode NATURAL ASCENDING
    SORTED -> Statistiques_Mode_Groupe_km (writer XLSXW_2)
Statistiques_Mode_Groupe_km (writer XLSXW_2)
    attributes: id_mode number(20), nom_mode string(100), alias_mode string(100), nb_km_parcourus_pendulaires_groupe number(20), nb_km_parcourus_pro_groupe number(20)

Bookmark: Statistiques modes pour le Groupe, nombre de déplacements
Note: public.deplacements_mode
Junction_4
    -> FeatureMerger_19 [REQUESTOR]
Tester_Motif_defini_D-T
    BOOL_OP = OR
    TEST_CLAUSE:
      TEST @Value(motif_defini_id) = 1
      TEST @Value(motif_defini_id) = 2
      TEST @Value(motif_defini_id) = 3
      TEST @Value(motif_defini_id) = 4
      TEST @Value(motif_defini_id) = 6
      TEST @Value(motif_defini_id) = 7
    TEST_MODE = TEST
    PASSED -> StatisticsCalculator_Mode
    PASSED -> StatisticsCalculator_Motif_defini
    PASSED -> StatisticsCalculator_nb_mode_par_utilisateur_D-T
    PASSED -> StatisticsCalculator_nb_depl_par_utilisateur_D-T
StatisticsCalculator_Mode
    CALCULATION_MODE = NUMERIC
    FEAT_STATS = id_deplacement,NUMERIC_MODE,,,COUNT,,,,,,,,,,
    GROUP_BY = mode_id
    SUMMARY -> FeatureMerger_19 [SUPPLIER]
FeatureMerger_19
    ATTR_ACCUM_MODE = Merge Supplier
    ATTR_CONFLICT_RES = Use Requestor
    IGNORE_NULLS = No
    JOIN_KEYS = @Value(id_mode) @Value(mode_id) AUTO
    MERGE_TYPE = Attributes Only
    PROCESS_DUPS = NO
    REJECT_NULL_MISSING_KEYS = No
    SUPPLIERS_FIRST = No
    MERGED -> AttributeManager_5
    UNMERGED_REQUESTOR -> AttributeManager_5
AttributeManager_5
    ATTR_TABLE = RENAME_SET_VALUE id_deplacement.total_count > nb_depl_pendulaires_groupe = FME_CONDITIONAL:DEFAULT_VALUE'_FME_NO_OP_'BOOL_OP;OR;COMPOSITE_TEST;1;TEST nb_depl_pendulaires_groupe ATTRIBUTE_IS_MISSING _FME_BLANK_STRING_'0'FME_NUM_CONDITIONS2___
    -> FeatureMerger_20 [REQUESTOR]
Tester_Motif_defini_Pro
    BOOL_OP = OR
    TEST_CLAUSE:
      TEST @Value(motif_defini_id) = 5
      TEST @Value(motif_defini_id) = 8
    TEST_MODE = TEST
    PASSED -> StatisticsCalculator_Mode_2
    PASSED -> StatisticsCalculator_Motif_defini
    PASSED -> StatisticsCalculator_nb_mode_par_utilisateur_pro
    PASSED -> StatisticsCalculator_nb_depl_par_utilisateur_pro
StatisticsCalculator_Mode_2
    CALCULATION_MODE = NUMERIC
    FEAT_STATS = id_deplacement,NUMERIC_MODE,,,COUNT,,,,,,,,,,
    GROUP_BY = mode_id
    SUMMARY -> FeatureMerger_20 [SUPPLIER]
FeatureMerger_20
    ATTR_ACCUM_MODE = Merge Supplier
    ATTR_CONFLICT_RES = Use Requestor
    IGNORE_NULLS = No
    JOIN_KEYS = @Value(id_mode) @Value(mode_id) AUTO
    MERGE_TYPE = Attributes Only
    PROCESS_DUPS = NO
    REJECT_NULL_MISSING_KEYS = No
    SUPPLIERS_FIRST = No
    MERGED -> AttributeManager_16
    UNMERGED_REQUESTOR -> AttributeManager_16
AttributeManager_16
    ATTR_TABLE = RENAME_SET_VALUE id_deplacement.total_count > nb_depl_pro_groupe = FME_CONDITIONAL:DEFAULT_VALUE'_FME_NO_OP_'BOOL_OP;OR;COMPOSITE_TEST;1;TEST nb_depl_pro_groupe ATTRIBUTE_IS_MISSING _FME_BLANK_STRING_'0'FME_NUM_CONDITIONS2___
    -> Sorter_2
Sorter_2
    SORT_PARM = id_mode NATURAL ASCENDING
    SORTED -> Statistiques_Mode_Groupe (writer XLSXW_2)
Statistiques_Mode_Groupe (writer XLSXW_2)
    attributes: id_mode number(20), nom_mode string(100), alias_mode string(100), nb_depl_pendulaires_groupe number(20), nb_depl_pro_groupe number(20)

Bookmark: Statistiques par mode et par raison D-T et pro, nombre de déplacements
Note: public.deplacements_mode
Junction_6
    -> FeatureMerger_29 [REQUESTOR]
Note: public.deplacements_mode
Junction_8
    -> FeatureMerger_28 [REQUESTOR]
Tester_Motif_defini_D-T_4
    BOOL_OP = OR
    TEST_CLAUSE:
      TEST @Value(motif_defini_id) = 1
      TEST @Value(motif_defini_id) = 2
      TEST @Value(motif_defini_id) = 3
      TEST @Value(motif_defini_id) = 4
      TEST @Value(motif_defini_id) = 6
      TEST @Value(motif_defini_id) = 7
    TEST_MODE = TEST
    PASSED -> AttributeManager_21
AttributeManager_21
    ATTR_TABLE:
      SET_TO raison_1_D-T = FME_CONDITIONAL:DEFAULT_VALUE'0'BOOL_OP;OR;COMPOSITE_TEST;1;TEST @Value(raison_id) = 1'1'FME_NUM_CONDITIONS2___
      SET_TO raison_2_D-T = FME_CONDITIONAL:DEFAULT_VALUE'0'BOOL_OP;OR;COMPOSITE_TEST;1;TEST @Value(raison_id) = 2'1'FME_NUM_CONDITIONS2___
      SET_TO raison_4_D-T = FME_CONDITIONAL:DEFAULT_VALUE'0'BOOL_OP;OR;COMPOSITE_TEST;1;TEST @Value(raison_id) = 4'1'FME_NUM_CONDITIONS2___
      SET_TO raison_5_D-T = FME_CONDITIONAL:DEFAULT_VALUE'0'BOOL_OP;OR;COMPOSITE_TEST;1;TEST @Value(raison_id) = 5'1'FME_NUM_CONDITIONS2___
      SET_TO raison_6_D-T = FME_CONDITIONAL:DEFAULT_VALUE'0'BOOL_OP;OR;COMPOSITE_TEST;1;TEST @Value(raison_id) = 6'1'FME_NUM_CONDITIONS2___
      SET_TO raison_7_D-T = FME_CONDITIONAL:DEFAULT_VALUE'0'BOOL_OP;OR;COMPOSITE_TEST;1;TEST @Value(raison_id) = 7'1'FME_NUM_CONDITIONS2___
      SET_TO raison_8_D-T = FME_CONDITIONAL:DEFAULT_VALUE'0'BOOL_OP;OR;COMPOSITE_TEST;1;TEST @Value(raison_id) = 8'1'FME_NUM_CONDITIONS2___
      SET_TO raison_9_D-T = FME_CONDITIONAL:DEFAULT_VALUE'0'BOOL_OP;OR;COMPOSITE_TEST;1;TEST @Value(raison_id) = 9'1'FME_NUM_CONDITIONS2___
      SET_TO raison_10_D-T = FME_CONDITIONAL:DEFAULT_VALUE'0'BOOL_OP;OR;COMPOSITE_TEST;1;TEST @Value(raison_id) = 10'1'FME_NUM_CONDITIONS2___
      SET_TO raison_11_D-T = FME_CONDITIONAL:DEFAULT_VALUE'0'BOOL_OP;OR;COMPOSITE_TEST;1;TEST @Value(raison_id) = 11'1'FME_NUM_CONDITIONS2___
      SET_TO raison_12_D-T = FME_CONDITIONAL:DEFAULT_VALUE'0'BOOL_OP;OR;COMPOSITE_TEST;1;TEST @Value(raison_id) = 12'1'FME_NUM_CONDITIONS2___
      SET_TO raison_13_D-T = FME_CONDITIONAL:DEFAULT_VALUE'0'BOOL_OP;OR;COMPOSITE_TEST;1;TEST @Value(raison_id) = 13'1'FME_NUM_CONDITIONS2___
      SET_TO raison_14_D-T = FME_CONDITIONAL:DEFAULT_VALUE'0'BOOL_OP;OR;COMPOSITE_TEST;1;TEST @Value(raison_id) = 14'1'FME_NUM_CONDITIONS2___
      SET_TO raison_15_D-T = FME_CONDITIONAL:DEFAULT_VALUE'0'BOOL_OP;OR;COMPOSITE_TEST;1;TEST @Value(raison_id) = 15'1'FME_NUM_CONDITIONS2___
      SET_TO raison_16_D-T = FME_CONDITIONAL:DEFAULT_VALUE'0'BOOL_OP;OR;COMPOSITE_TEST;1;TEST @Value(raison_id) = 16'1'FME_NUM_CONDITIONS2___
      SET_TO
    -> Aggregator_8
Aggregator_8
    ACCUM_ATTRS_NAME = Drop Incoming Attributes
    AGGREGATE_TYPE = Homogeneous Collection (If Possible)
    GROUP_BY = mode_id
    MODE = Geometry - Assemble One Level
    SEP = ,
    SUM = raison_10_D-T raison_11_D-T raison_12_D-T raison_13_D-T raison_14_D-T raison_15_D-T raison_16_D-T raison_1_D-T raison_2_D-T raison_4_D-T raison_5_D-T raison_6_D-T raison_7_D-T raison_8_D-T raison_9_D-T
    AGGREGATE -> FeatureMerger_28 [SUPPLIER]
FeatureMerger_28
    ATTR_ACCUM_MODE = Merge Supplier
    ATTR_CONFLICT_RES = Use Requestor
    IGNORE_NULLS = No
    JOIN_KEYS = @Value(id_mode) @Value(mode_id) AUTO
    MERGE_TYPE = Attributes Only
    PROCESS_DUPS = NO
    REJECT_NULL_MISSING_KEYS = No
    SUPPLIERS_FIRST = No
    MERGED -> Sorter_5
    UNMERGED_REQUESTOR -> Sorter_5
Sorter_5
    SORT_PARM = id_mode NATURAL ASCENDING
    SORTED -> Statistiques_Mode_Raison_D-T (writer XLSXW_2)
Statistiques_Mode_Raison_D-T (writer XLSXW_2)
    attributes: id_mode number(20), nom_mode string(100), alias_mode string(100), raison_1_D-T string(200), raison_2_D-T string(200), raison_4_D-T string(200), raison_5_D-T string(200), raison_6_D-T string(200), raison_7_D-T string(200), raison_8_D-T string(200), raison_9_D-T string(200), raison_10_D-T string(200), raison_11_D-T string(200), raison_12_D-T string(200), raison_13_D-T string(200), raison_14_D-T string(200), raison_15_D-T string(200), raison_16_D-T string(200)
Tester_Motif_defini_Pro_4
    BOOL_OP = OR
    TEST_CLAUSE:
      TEST @Value(motif_defini_id) = 5
      TEST @Value(motif_defini_id) = 8
    TEST_MODE = TEST
    PASSED -> AttributeManager_25
AttributeManager_25
    ATTR_TABLE:
      SET_TO raison_1_Pro = FME_CONDITIONAL:DEFAULT_VALUE'0'BOOL_OP;OR;COMPOSITE_TEST;1;TEST @Value(raison_id) = 1'1'FME_NUM_CONDITIONS2___
      SET_TO raison_2_Pro = FME_CONDITIONAL:DEFAULT_VALUE'0'BOOL_OP;OR;COMPOSITE_TEST;1;TEST @Value(raison_id) = 2'1'FME_NUM_CONDITIONS2___
      SET_TO raison_4_Pro = FME_CONDITIONAL:DEFAULT_VALUE'0'BOOL_OP;OR;COMPOSITE_TEST;1;TEST @Value(raison_id) = 4'1'FME_NUM_CONDITIONS2___
      SET_TO raison_5_Pro = FME_CONDITIONAL:DEFAULT_VALUE'0'BOOL_OP;OR;COMPOSITE_TEST;1;TEST @Value(raison_id) = 5'1'FME_NUM_CONDITIONS2___
      SET_TO raison_6_Pro = FME_CONDITIONAL:DEFAULT_VALUE'0'BOOL_OP;OR;COMPOSITE_TEST;1;TEST @Value(raison_id) = 6'1'FME_NUM_CONDITIONS2___
      SET_TO raison_7_Pro = FME_CONDITIONAL:DEFAULT_VALUE'0'BOOL_OP;OR;COMPOSITE_TEST;1;TEST @Value(raison_id) = 7'1'FME_NUM_CONDITIONS2___
      SET_TO raison_8_Pro = FME_CONDITIONAL:DEFAULT_VALUE'0'BOOL_OP;OR;COMPOSITE_TEST;1;TEST @Value(raison_id) = 8'1'FME_NUM_CONDITIONS2___
      SET_TO raison_9_Pro = FME_CONDITIONAL:DEFAULT_VALUE'0'BOOL_OP;OR;COMPOSITE_TEST;1;TEST @Value(raison_id) = 9'1'FME_NUM_CONDITIONS2___
      SET_TO raison_10_Pro = FME_CONDITIONAL:DEFAULT_VALUE'0'BOOL_OP;OR;COMPOSITE_TEST;1;TEST @Value(raison_id) = 10'1'FME_NUM_CONDITIONS2___
      SET_TO raison_11_Pro = FME_CONDITIONAL:DEFAULT_VALUE'0'BOOL_OP;OR;COMPOSITE_TEST;1;TEST @Value(raison_id) = 11'1'FME_NUM_CONDITIONS2___
      SET_TO raison_12_Pro = FME_CONDITIONAL:DEFAULT_VALUE'0'BOOL_OP;OR;COMPOSITE_TEST;1;TEST @Value(raison_id) = 12'1'FME_NUM_CONDITIONS2___
      SET_TO raison_13_Pro = FME_CONDITIONAL:DEFAULT_VALUE'0'BOOL_OP;OR;COMPOSITE_TEST;1;TEST @Value(raison_id) = 13'1'FME_NUM_CONDITIONS2___
      SET_TO raison_14_Pro = FME_CONDITIONAL:DEFAULT_VALUE'0'BOOL_OP;OR;COMPOSITE_TEST;1;TEST @Value(raison_id) = 14'1'FME_NUM_CONDITIONS2___
      SET_TO raison_15_Pro = FME_CONDITIONAL:DEFAULT_VALUE'0'BOOL_OP;OR;COMPOSITE_TEST;1;TEST @Value(raison_id) = 15'1'FME_NUM_CONDITIONS2___
      SET_TO raison_16_Pro = FME_CONDITIONAL:DEFAULT_VALUE'0'BOOL_OP;OR;COMPOSITE_TEST;1;TEST @Value(raison_id) = 16'1'FME_NUM_CONDITIONS2___
      SET_TO
    -> Aggregator_9
Aggregator_9
    ACCUM_ATTRS_NAME = Drop Incoming Attributes
    AGGREGATE_TYPE = Homogeneous Collection (If Possible)
    GROUP_BY = mode_id
    MODE = Geometry - Assemble One Level
    SEP = ,
    SUM = raison_10_Pro raison_11_Pro raison_12_Pro raison_13_Pro raison_14_Pro raison_15_Pro raison_16_Pro raison_1_Pro raison_2_Pro raison_4_Pro raison_5_Pro raison_6_Pro raison_7_Pro raison_9_Pro raison_8_Pro
    AGGREGATE -> FeatureMerger_29 [SUPPLIER]
FeatureMerger_29
    ATTR_ACCUM_MODE = Merge Supplier
    ATTR_CONFLICT_RES = Use Requestor
    IGNORE_NULLS = No
    JOIN_KEYS = @Value(id_mode) @Value(mode_id) AUTO
    MERGE_TYPE = Attributes Only
    PROCESS_DUPS = NO
    REJECT_NULL_MISSING_KEYS = No
    SUPPLIERS_FIRST = No
    MERGED -> Sorter_6
    UNMERGED_REQUESTOR -> Sorter_6
Sorter_6
    SORT_PARM = id_mode NATURAL ASCENDING
    SORTED -> Statistiques_Mode_Raison_PRO (writer XLSXW_2)
Statistiques_Mode_Raison_PRO (writer XLSXW_2)
    attributes: id_mode number(20), nom_mode string(100), alias_mode string(100), raison_1_Pro string(200), raison_2_Pro string(200), raison_4_Pro string(200), raison_5_Pro string(200), raison_6_Pro string(200), raison_7_Pro string(200), raison_8_Pro string(200), raison_9_Pro string(200), raison_10_Pro string(200), raison_11_Pro string(200), raison_12_Pro string(200), raison_13_Pro string(200), raison_14_Pro string(200), raison_15_Pro string(200), raison_16_Pro string(200)

Bookmark: Gestion des clés étrangères des lieux
deplacements_type (reader POSTGRES_1)
    attributes: id_type serial,PrimaryKey, nom_type varchar(100), alias_type varchar(100)
    -> FeatureMerger_9 [SUPPLIER]
deplacements_lieu (reader POSTGIS_1)
    attributes: id serial,PrimaryKey, nom varchar(100), rue varchar(100), no_entree varchar(10), npa int4, localite varchar(50), utilisateur_id int4,BTREE, type_id int4,BTREE
    -> AttributeManager_3
AttributeManager_3
    ATTR_TABLE = RENAME_SET_VALUE id > id_lieu
    -> FeatureMerger_9 [REQUESTOR]
FeatureMerger_9
    ATTR_ACCUM_MODE = Merge Supplier
    ATTR_CONFLICT_RES = Use Requestor
    IGNORE_NULLS = No
    JOIN_KEYS = @Value(type_id) @Value(id_type) AUTO
    MERGE_TYPE = Attributes and Geometry
    PROCESS_DUPS = NO
    REJECT_NULL_MISSING_KEYS = No
    SUPPLIERS_FIRST = No
    MERGED -> AttributeManager_2

Bookmark: Gestion des clés étrangères des profils des utilisateurs.trices
deplacements_profil (reader POSTGRES_1)
    attributes: id_profil serial,PrimaryKey, pmr bool, bike_to_work bool, fonction_id int4,BTREE, site_id int4,BTREE, societe_id int4,BTREE, taux_id int4,BTREE, utilisateur_id int4,Unique, teletravail_id int4,BTREE
    -> FeatureMerger_10 [REQUESTOR]
deplacements_societe (reader POSTGRES_1)
    attributes: id_societe serial,PrimaryKey, nom_societe varchar(100)
    -> FeatureMerger_10 [SUPPLIER]
    -> FeatureMerger_30 [REQUESTOR]
    -> Junction_9
    -> Junction_11
FeatureMerger_10
    ATTR_ACCUM_MODE = Merge Supplier
    ATTR_CONFLICT_RES = Use Requestor
    IGNORE_NULLS = No
    JOIN_KEYS = @Value(societe_id) @Value(id_societe) AUTO
    MERGE_TYPE = Attributes Only
    PROCESS_DUPS = NO
    REJECT_NULL_MISSING_KEYS = No
    SUPPLIERS_FIRST = No
    MERGED -> FeatureMerger_11 [REQUESTOR]
Note: FeatureMerger_27 : Requestor
Junction_11
    -> Junction_12
Note: FeatureMerger_22 : Requestor
Junction_9
    -> Junction_10
deplacements_site (reader POSTGRES_1)
    attributes: id_site serial,PrimaryKey, nom_site varchar(100), lieu_id int4,BTREE
    -> FeatureMerger_11 [SUPPLIER]
    -> FeatureMerger_31 [REQUESTOR]
    -> Junction_13
    -> Junction_17
FeatureMerger_11
    ATTR_ACCUM_MODE = Merge Supplier
    ATTR_CONFLICT_RES = Use Requestor
    IGNORE_NULLS = No
    JOIN_KEYS = @Value(site_id) @Value(id_site) AUTO
    MERGE_TYPE = Attributes Only
    PROCESS_DUPS = NO
    REJECT_NULL_MISSING_KEYS = No
    SUPPLIERS_FIRST = No
    MERGED -> FeatureMerger_12 [REQUESTOR]
Note: FeatureMerger_25 : Requestor
Junction_17
    -> Junction_18
Note: FeatureMerger_42 : Requestor
Junction_13
    -> Junction_14
deplacements_fonction (reader POSTGRES_1)
    attributes: id_fonction serial,PrimaryKey, nom_fonction varchar(100), alias_fonction varchar(100)
    -> FeatureMerger_12 [SUPPLIER]
    -> FeatureMerger_32 [REQUESTOR]
FeatureMerger_12
    ATTR_ACCUM_MODE = Merge Supplier
    ATTR_CONFLICT_RES = Use Requestor
    IGNORE_NULLS = No
    JOIN_KEYS = @Value(fonction_id) @Value(id_fonction) AUTO
    MERGE_TYPE = Attributes Only
    PROCESS_DUPS = NO
    REJECT_NULL_MISSING_KEYS = No
    SUPPLIERS_FIRST = No
    MERGED -> FeatureMerger_13 [REQUESTOR]
deplacements_taux (reader POSTGRES_1)
    attributes: id_taux serial,PrimaryKey, taux varchar(3)
    -> FeatureMerger_13 [SUPPLIER]
    -> FeatureMerger_33 [REQUESTOR]
FeatureMerger_13
    ATTR_ACCUM_MODE = Merge Supplier
    ATTR_CONFLICT_RES = Use Requestor
    IGNORE_NULLS = No
    JOIN_KEYS = @Value(taux_id) @Value(id_taux) AUTO
    MERGE_TYPE = Attributes Only
    PROCESS_DUPS = NO
    REJECT_NULL_MISSING_KEYS = No
    SUPPLIERS_FIRST = No
    MERGED -> FeatureMerger_14 [REQUESTOR]
deplacements_teletravail (reader POSTGRES_1)
    attributes: id_teletravail serial,PrimaryKey, teletravail varchar(3)
    -> FeatureMerger_14 [SUPPLIER]
    -> FeatureMerger_34 [REQUESTOR]
FeatureMerger_14
    ATTR_ACCUM_MODE = Merge Supplier
    ATTR_CONFLICT_RES = Use Requestor
    IGNORE_NULLS = No
    JOIN_KEYS = @Value(teletravail_id) @Value(id_teletravail) AUTO
    MERGE_TYPE = Attributes Only
    PROCESS_DUPS = NO
    REJECT_NULL_MISSING_KEYS = No
    SUPPLIERS_FIRST = No
    MERGED -> AttributeManager_15
AttributeManager_15
    ATTR_TABLE:
      REMOVE id_profil
      REMOVE id_societe
      REMOVE id_site
      REMOVE id_fonction
      REMOVE id_taux
      REMOVE id_teletravail
    -> FeatureMerger_16 [SUPPLIER]
deplacements_societe_sites (reader POSTGRES_1)
    attributes: id int8,PrimaryKey, societe_id int4,BTREE, site_id int4,BTREE

Bookmark: Statistiques modes par société, nombre de kilomètres
Note: public.deplacements_societe
Junction_12
    -> FeatureMerger_27 [REQUESTOR]
Note: FeatureMerger_16 : Merged
Junction_20
    -> FeatureMerger_64 [SUPPLIER]
Note: FeatureMerger_16 : Merged
Junction_22
    -> FeatureMerger_63 [SUPPLIER]
Tester_Motif_defini_D-T_6
    BOOL_OP = OR
    TEST_CLAUSE:
      TEST @Value(motif_defini_id) = 1
      TEST @Value(motif_defini_id) = 2
      TEST @Value(motif_defini_id) = 3
      TEST @Value(motif_defini_id) = 4
      TEST @Value(motif_defini_id) = 6
      TEST @Value(motif_defini_id) = 7
    TEST_MODE = TEST
    PASSED -> AttributeManager_8
    PASSED -> StatisticsCalculator_14
    PASSED -> FeatureMerger_63 [REQUESTOR]
AttributeManager_8
    ATTR_TABLE:
      SET_TO mode_1_D-T = FME_CONDITIONAL:DEFAULT_VALUE'0'BOOL_OP;OR;COMPOSITE_TEST;1;TEST @Value(mode_id) = 1'@Value(distance_voiture_km)'FME_NUM_CONDITIONS2___
      SET_TO mode_2_D-T = FME_CONDITIONAL:DEFAULT_VALUE'0'BOOL_OP;OR;COMPOSITE_TEST;1;TEST @Value(mode_id) = 2'@Value(distance_voiture_km)'FME_NUM_CONDITIONS2___
      SET_TO mode_3_D-T = FME_CONDITIONAL:DEFAULT_VALUE'0'BOOL_OP;OR;COMPOSITE_TEST;1;TEST @Value(mode_id) = 3'@Value(distance_voiture_km)'FME_NUM_CONDITIONS2___
      SET_TO mode_4_D-T = FME_CONDITIONAL:DEFAULT_VALUE'0'BOOL_OP;OR;COMPOSITE_TEST;1;TEST @Value(mode_id) = 4'@Value(distance_voiture_km)'FME_NUM_CONDITIONS2___
      SET_TO mode_5_D-T = FME_CONDITIONAL:DEFAULT_VALUE'0'BOOL_OP;OR;COMPOSITE_TEST;1;TEST @Value(mode_id) = 5'@Value(distance_voiture_km)'FME_NUM_CONDITIONS2___
      SET_TO mode_6_D-T = FME_CONDITIONAL:DEFAULT_VALUE'0'BOOL_OP;OR;COMPOSITE_TEST;1;TEST @Value(mode_id) = 6'@Value(distance_voiture_km)'FME_NUM_CONDITIONS2___
      SET_TO mode_7_D-T = FME_CONDITIONAL:DEFAULT_VALUE'0'BOOL_OP;OR;COMPOSITE_TEST;1;TEST @Value(mode_id) = 7'@Value(distance_velo_km)'FME_NUM_CONDITIONS2___
      SET_TO mode_8_D-T = FME_CONDITIONAL:DEFAULT_VALUE'0'BOOL_OP;OR;COMPOSITE_TEST;1;TEST @Value(mode_id) = 8'@Value(distance_voiture_km)'FME_NUM_CONDITIONS2___
      SET_TO mode_9_D-T = FME_CONDITIONAL:DEFAULT_VALUE'0'BOOL_OP;OR;COMPOSITE_TEST;1;TEST @Value(mode_id) = 9'@Value(distance_voiture_km)'FME_NUM_CONDITIONS2___
      SET_TO mode_10_D-T = FME_CONDITIONAL:DEFAULT_VALUE'0'BOOL_OP;OR;COMPOSITE_TEST;1;TEST @Value(mode_id) = 10'@Value(distance_voiture_km)'FME_NUM_CONDITIONS2___
      SET_TO mode_11_D-T = FME_CONDITIONAL:DEFAULT_VALUE'0'BOOL_OP;OR;COMPOSITE_TEST;1;TEST @Value(mode_id) = 11'@Value(distance_marche_km)'FME_NUM_CONDITIONS2___
      SET_TO mode_12_D-T = FME_CONDITIONAL:DEFAULT_VALUE'0'BOOL_OP;OR;COMPOSITE_TEST;1;TEST @Value(mode_id) = 12'@Value(distance_marche_km)'FME_NUM_CONDITIONS2___
      SET_TO mode_13_D-T = FME_CONDITIONAL:DEFAULT_VALUE'0'BOOL_OP;OR;COMPOSITE_TEST;1;TEST @Value(mode_id) = 13'@Value(distance_voiture_km)'FME_NUM_CONDITIONS2___
      SET_TO mode_14_D-T = FME_CONDITIONAL:DEFAULT_VALUE'_FME_NO_OP_'BOOL_OP;OR;COMPOSITE_TEST;1;TEST @Value(mode_id) = 14'@Value(distance_voiture_km)'FME_NUM_CONDITIONS2___
      SET_TO mode_15_D-T = FME_CONDITIONAL:DEFAULT_VALUE'0'BOOL_OP;OR;COMPOSITE_TEST;1;TEST @Value(mode_id) = 15'@Value(distance_voiture_km)'FME_NUM_CONDITIONS2___
      SET_TO mode_16_D-T = FME_CONDITIONAL:DEFAULT_VALUE'0'BOOL_OP;OR;COMPOSITE_TEST;1;TEST @Value(mode_id) = 16'@Value(distance_voiture_km)'FME_NUM_CONDITIONS2___
      SET_TO
    -> Aggregator_4
Aggregator_4
    ACCUM_ATTRS_NAME = Drop Incoming Attributes
    AGGREGATE_TYPE = Homogeneous Collection (If Possible)
    GROUP_BY = societe_id
    MODE = Geometry - Assemble One Level
    SEP = ,
    SUM = mode_1_D-T mode_2_D-T mode_10_D-T mode_11_D-T mode_12_D-T mode_13_D-T mode_14_D-T mode_15_D-T mode_16_D-T mode_3_D-T mode_4_D-T mode_5_D-T mode_6_D-T mode_7_D-T mode_8_D-T mode_9_D-T
    AGGREGATE -> FeatureMerger_27 [SUPPLIER]
FeatureMerger_27
    ATTR_ACCUM_MODE = Merge Supplier
    ATTR_CONFLICT_RES = Use Requestor
    IGNORE_NULLS = No
    JOIN_KEYS = @Value(id_societe) @Value(societe_id) AUTO
    MERGE_TYPE = Attributes Only
    PROCESS_DUPS = NO
    REJECT_NULL_MISSING_KEYS = No
    SUPPLIERS_FIRST = No
    MERGED -> FeatureMerger_41 [REQUESTOR]
    UNMERGED_REQUESTOR -> FeatureMerger_41 [REQUESTOR]
StatisticsCalculator_14
    CALCULATION_MODE = NUMERIC
    FEAT_STATS = id_deplacement,NUMERIC_MODE,,,COUNT,,,,,,,,,,
    GROUP_BY = societe_id
    SUMMARY -> AttributeRenamer
AttributeRenamer
    ATTR_TABLE = RENAME_SET_DEFAULT id_deplacement.total_count > nb_depl_pendulaires
    MISSING_INPUT_ATTRS = REMOVE
    -> FeatureMerger_50 [REQUESTOR]
FeatureMerger_63
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    USED_SUPPLIER -> StatisticsCalculator_11
StatisticsCalculator_11
    CALCULATION_MODE = NUMERIC
    FEAT_STATS = utilisateur_id,NUMERIC_MODE,,,COUNT,,,,,,,,,,
    GROUP_BY = societe_id
    SUMMARY -> AttributeRenamer_13
AttributeRenamer_13
    ATTR_TABLE = RENAME_SET_DEFAULT utilisateur_id.total_count > nb_utilisateurs_D-T
    MISSING_INPUT_ATTRS = REMOVE
    -> FeatureMerger_51 [SUPPLIER]
Tester_Motif_defini_Pro_6
    BOOL_OP = OR
    TEST_CLAUSE:
      TEST @Value(motif_defini_id) = 5
      TEST @Value(motif_defini_id) = 8
    TEST_MODE = TEST
    PASSED -> AttributeManager_9
    PASSED -> StatisticsCalculator_15
    PASSED -> FeatureMerger_64 [REQUESTOR]
AttributeManager_9
    ATTR_TABLE:
      SET_TO mode_1_Pro = FME_CONDITIONAL:DEFAULT_VALUE'0'BOOL_OP;OR;COMPOSITE_TEST;1;TEST @Value(mode_id) = 1'@Value(distance_voiture_km)'FME_NUM_CONDITIONS2___
      SET_TO mode_2_Pro = FME_CONDITIONAL:DEFAULT_VALUE'0'BOOL_OP;OR;COMPOSITE_TEST;1;TEST @Value(mode_id) = 2'@Value(distance_voiture_km)'FME_NUM_CONDITIONS2___
      SET_TO mode_3_Pro = FME_CONDITIONAL:DEFAULT_VALUE'0'BOOL_OP;OR;COMPOSITE_TEST;1;TEST @Value(mode_id) = 3'@Value(distance_voiture_km)'FME_NUM_CONDITIONS2___
      SET_TO mode_4_Pro = FME_CONDITIONAL:DEFAULT_VALUE'0'BOOL_OP;OR;COMPOSITE_TEST;1;TEST @Value(mode_id) = 4'@Value(distance_voiture_km)'FME_NUM_CONDITIONS2___
      SET_TO mode_5_Pro = FME_CONDITIONAL:DEFAULT_VALUE'0'BOOL_OP;OR;COMPOSITE_TEST;1;TEST @Value(mode_id) = 5'@Value(distance_voiture_km)'FME_NUM_CONDITIONS2___
      SET_TO mode_6_Pro = FME_CONDITIONAL:DEFAULT_VALUE'0'BOOL_OP;OR;COMPOSITE_TEST;1;TEST @Value(mode_id) = 6'@Value(distance_voiture_km)'FME_NUM_CONDITIONS2___
      SET_TO mode_7_Pro = FME_CONDITIONAL:DEFAULT_VALUE'0'BOOL_OP;OR;COMPOSITE_TEST;1;TEST @Value(mode_id) = 7'@Value(distance_velo_km)'FME_NUM_CONDITIONS2___
      SET_TO mode_8_Pro = FME_CONDITIONAL:DEFAULT_VALUE'0'BOOL_OP;OR;COMPOSITE_TEST;1;TEST @Value(mode_id) = 8'@Value(distance_voiture_km)'FME_NUM_CONDITIONS2___
      SET_TO mode_9_Pro = FME_CONDITIONAL:DEFAULT_VALUE'0'BOOL_OP;OR;COMPOSITE_TEST;1;TEST @Value(mode_id) = 9'@Value(distance_voiture_km)'FME_NUM_CONDITIONS2___
      SET_TO mode_10_Pro = FME_CONDITIONAL:DEFAULT_VALUE'0'BOOL_OP;OR;COMPOSITE_TEST;1;TEST @Value(mode_id) = 10'@Value(distance_voiture_km)'FME_NUM_CONDITIONS2___
      SET_TO mode_11_Pro = FME_CONDITIONAL:DEFAULT_VALUE'0'BOOL_OP;OR;COMPOSITE_TEST;1;TEST @Value(mode_id) = 11'@Value(distance_marche_km)'FME_NUM_CONDITIONS2___
      SET_TO mode_12_Pro = FME_CONDITIONAL:DEFAULT_VALUE'0'BOOL_OP;OR;COMPOSITE_TEST;1;TEST @Value(mode_id) = 12'@Value(distance_marche_km)'FME_NUM_CONDITIONS2___
      SET_TO mode_13_Pro = FME_CONDITIONAL:DEFAULT_VALUE'0'BOOL_OP;OR;COMPOSITE_TEST;1;TEST @Value(mode_id) = 13'@Value(distance_voiture_km)'FME_NUM_CONDITIONS2___
      SET_TO mode_14_Pro = FME_CONDITIONAL:DEFAULT_VALUE'0'BOOL_OP;OR;COMPOSITE_TEST;1;TEST @Value(mode_id) = 14'@Value(distance_voiture_km)'FME_NUM_CONDITIONS2___
      SET_TO mode_15_Pro = FME_CONDITIONAL:DEFAULT_VALUE'0'BOOL_OP;OR;COMPOSITE_TEST;1;TEST @Value(mode_id) = 15'@Value(distance_voiture_km)'FME_NUM_CONDITIONS2___
      SET_TO mode_16_Pro = FME_CONDITIONAL:DEFAULT_VALUE'0'BOOL_OP;OR;COMPOSITE_TEST;1;TEST @Value(mode_id) = 16'@Value(distance_voiture_km)'FME_NUM_CONDITIONS2___
      SET_TO
    -> Aggregator_7
Aggregator_7
    ACCUM_ATTRS_NAME = Drop Incoming Attributes
    AGGREGATE_TYPE = Homogeneous Collection (If Possible)
    GROUP_BY = societe_id
    MODE = Geometry - Assemble One Level
    SEP = ,
    SUM = mode_10_Pro mode_11_Pro mode_12_Pro mode_13_Pro mode_14_Pro mode_15_Pro mode_16_Pro mode_1_Pro mode_2_Pro mode_3_Pro mode_4_Pro mode_5_Pro mode_6_Pro mode_7_Pro mode_8_Pro mode_9_Pro
    AGGREGATE -> FeatureMerger_41 [SUPPLIER]
FeatureMerger_41
    ATTR_ACCUM_MODE = Merge Supplier
    ATTR_CONFLICT_RES = Use Requestor
    IGNORE_NULLS = No
    JOIN_KEYS = @Value(id_societe) @Value(societe_id) AUTO
    MERGE_TYPE = Attributes Only
    PROCESS_DUPS = NO
    REJECT_NULL_MISSING_KEYS = No
    SUPPLIERS_FIRST = No
    MERGED -> FeatureMerger_46 [REQUESTOR]
    UNMERGED_REQUESTOR -> FeatureMerger_46 [REQUESTOR]
StatisticsCalculator_15
    CALCULATION_MODE = NUMERIC
    FEAT_STATS = id_deplacement,NUMERIC_MODE,,,COUNT,,,,,,,,,,
    GROUP_BY = societe_id
    SUMMARY -> AttributeRenamer_2
AttributeRenamer_2
    ATTR_TABLE = RENAME_SET_DEFAULT id_deplacement.total_count > nb_depl_pro
    MISSING_INPUT_ATTRS = REMOVE
    -> FeatureMerger_50 [SUPPLIER]
FeatureMerger_50
    ATTR_ACCUM_MODE = Merge Supplier
    ATTR_CONFLICT_RES = Use Requestor
    IGNORE_NULLS = No
    JOIN_KEYS = @Value(societe_id) @Value(societe_id) AUTO
    MERGE_TYPE = Attributes Only
    PROCESS_DUPS = NO
    REJECT_NULL_MISSING_KEYS = No
    SUPPLIERS_FIRST = No
    MERGED -> FeatureMerger_51 [REQUESTOR]
    UNMERGED_REQUESTOR -> FeatureMerger_51 [REQUESTOR]
FeatureMerger_51
    ATTR_ACCUM_MODE = Merge Supplier
    ATTR_CONFLICT_RES = Use Requestor
    IGNORE_NULLS = No
    JOIN_KEYS = @Value(societe_id) @Value(societe_id) AUTO
    MERGE_TYPE = Attributes Only
    PROCESS_DUPS = NO
    REJECT_NULL_MISSING_KEYS = No
    SUPPLIERS_FIRST = No
    MERGED -> FeatureMerger_65 [REQUESTOR]
FeatureMerger_64
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    USED_SUPPLIER -> StatisticsCalculator_12
StatisticsCalculator_12
    CALCULATION_MODE = NUMERIC
    FEAT_STATS = utilisateur_id,NUMERIC_MODE,,,COUNT,,,,,,,,,,
    GROUP_BY = societe_id
    SUMMARY -> AttributeRenamer_14
AttributeRenamer_14
    ATTR_TABLE = RENAME_SET_DEFAULT utilisateur_id.total_count > nb_utilisateurs_pro
    MISSING_INPUT_ATTRS = REMOVE
    -> FeatureMerger_65 [SUPPLIER]
FeatureMerger_65
    ATTR_ACCUM_MODE = Merge Supplier
    ATTR_CONFLICT_RES = Use Requestor
    IGNORE_NULLS = No
    JOIN_KEYS = @Value(societe_id) @Value(societe_id) AUTO
    MERGE_TYPE = Attributes Only
    PROCESS_DUPS = NO
    REJECT_NULL_MISSING_KEYS = No
    SUPPLIERS_FIRST = No
    MERGED -> FeatureMerger_46 [SUPPLIER]
    UNMERGED_REQUESTOR -> FeatureMerger_46 [SUPPLIER]
FeatureMerger_46
    ATTR_ACCUM_MODE = Merge Supplier
    ATTR_CONFLICT_RES = Use Requestor
    IGNORE_NULLS = No
    JOIN_KEYS = @Value(id_societe) @Value(societe_id) AUTO
    MERGE_TYPE = Attributes Only
    PROCESS_DUPS = NO
    REJECT_NULL_MISSING_KEYS = No
    SUPPLIERS_FIRST = No
    MERGED -> AttributeManager_11
    UNMERGED_REQUESTOR -> AttributeManager_11
AttributeManager_11
    ATTR_TABLE:
      SET_TO mode_1_D-T = @Evaluate(@round(@Value(mode_1_D-T),0))
      SET_TO mode_2_D-T = @Evaluate(@round(@Value(mode_2_D-T),0))
      SET_TO mode_3_D-T = @Evaluate(@round(@Value(mode_3_D-T),0))
      SET_TO mode_4_D-T = @Evaluate(@round(@Value(mode_4_D-T),0))
      SET_TO mode_5_D-T = @Evaluate(@round(@Value(mode_5_D-T),0))
      SET_TO mode_6_D-T = @Evaluate(@round(@Value(mode_6_D-T),0))
      SET_TO mode_7_D-T = @Evaluate(@round(@Value(mode_7_D-T),0))
      SET_TO mode_8_D-T = @Evaluate(@round(@Value(mode_8_D-T),0))
      SET_TO mode_9_D-T = @Evaluate(@round(@Value(mode_9_D-T),0))
      SET_TO mode_10_D-T = @Evaluate(@round(@Value(mode_10_D-T),0))
      SET_TO mode_11_D-T = @Evaluate(@round(@Value(mode_11_D-T),0))
      SET_TO mode_12_D-T = @Evaluate(@round(@Value(mode_12_D-T),0))
      SET_TO mode_13_D-T = @Evaluate(@round(@Value(mode_13_D-T),0))
      SET_TO mode_14_D-T = @Evaluate(@round(@Value(mode_14_D-T),0))
      SET_TO mode_15_D-T = @Evaluate(@round(@Value(mode_15_D-T),0))
      SET_TO mode_16_D-T = @Evaluate(@round(@Value(mode_16_D-T),0))
      SET_TO mode_1_Pro = @Evaluate(@round(@Value(mode_1_Pro),0))
      SET_TO mode_2_Pro = @Evaluate(@round(@Value(mode_2_Pro),0))
      SET_TO mode_3_Pro = @Evaluate(@round(@Value(mode_3_Pro),0))
      SET_TO mode_4_Pro = @Evaluate(@round(@Value(mode_4_Pro),0))
      SET_TO mode_5_Pro = @Evaluate(@round(@Value(mode_5_Pro),0))
      SET_TO mode_6_Pro = @Evaluate(@round(@Value(mode_6_Pro),0))
      SET_TO mode_7_Pro = @Evaluate(@round(@Value(mode_7_Pro),0))
      SET_TO mode_8_Pro = @Evaluate(@round(@Value(mode_8_Pro),0))
      SET_TO mode_9_Pro = @Evaluate(@round(@Value(mode_9_Pro),0))
      SET_TO mode_10_Pro = @Evaluate(@round(@Value(mode_10_Pro),0))
      SET_TO mode_11_Pro = @Evaluate(@round(@Value(mode_11_Pro),0))
      SET_TO mode_12_Pro = @Evaluate(@round(@Value(mode_12_Pro),0))
      SET_TO mode_13_Pro = @Evaluate(@round(@Value(mode_13_Pro),0))
      SET_TO mode_14_Pro = @Evaluate(@round(@Value(mode_14_Pro),0))
      SET_TO mode_15_Pro = @Evaluate(@round(@Value(mode_15_Pro),0))
      SET_TO mode_16_Pro = @Evaluate(@round(@Value(mode_16_Pro),0))
    USER_EXPOSED_ATTRIBUTES = utilisateur_id.total_count
    -> Sorter_15
Sorter_15
    SORT_PARM = id_societe NATURAL ASCENDING
    SORTED -> Statistiques_Mode_Societes (writer XLSXW_4)
Statistiques_Mode_Societes (writer XLSXW_4)
    attributes: id_societe number(20), nom_societe string(100), mode_1_D-T string(200), mode_2_D-T string(200), mode_3_D-T string(200), mode_4_D-T string(200), mode_5_D-T string(200), mode_6_D-T string(200), mode_7_D-T string(200), mode_8_D-T string(200), mode_9_D-T string(200), mode_10_D-T string(200), mode_11_D-T string(200), mode_12_D-T string(200), mode_13_D-T string(200), mode_14_D-T string(200), mode_15_D-T string(200), mode_16_D-T string(200), mode_1_Pro string(200), mode_2_Pro string(200), mode_3_Pro string(200), mode_4_Pro string(200), mode_5_Pro string(200), mode_6_Pro string(200), mode_7_Pro string(200), mode_8_Pro string(200), mode_9_Pro string(200), mode_10_Pro string(200), mode_11_Pro string(200), mode_12_Pro string(200),
      mode_13_Pro string(200), mode_14_Pro string(200), mode_15_Pro string(200), mode_16_Pro string(200), nb_utilisateurs_D-T number(20), nb_depl_pendulaires number(20), nb_depl_pro number(20), nb_utilisateurs_pro number(20)

Bookmark: Statistiques modes par société, nombre de déplacements
Note: public.deplacements_societe
Junction_10
    -> FeatureMerger_22 [REQUESTOR]
Tester_Motif_defini_D-T_2
    BOOL_OP = OR
    TEST_CLAUSE:
      TEST @Value(motif_defini_id) = 1
      TEST @Value(motif_defini_id) = 2
      TEST @Value(motif_defini_id) = 3
      TEST @Value(motif_defini_id) = 4
      TEST @Value(motif_defini_id) = 6
      TEST @Value(motif_defini_id) = 7
    TEST_MODE = TEST
    PASSED -> AttributeManager_18
    PASSED -> FeatureMerger_54 [REQUESTOR]
AttributeManager_18
    ATTR_TABLE:
      SET_TO mode_1_D-T = FME_CONDITIONAL:DEFAULT_VALUE'0'BOOL_OP;OR;COMPOSITE_TEST;1;TEST @Value(mode_id) = 1'1'FME_NUM_CONDITIONS2___
      SET_TO mode_2_D-T = FME_CONDITIONAL:DEFAULT_VALUE'0'BOOL_OP;OR;COMPOSITE_TEST;1;TEST @Value(mode_id) = 2'1'FME_NUM_CONDITIONS2___
      SET_TO mode_3_D-T = FME_CONDITIONAL:DEFAULT_VALUE'0'BOOL_OP;OR;COMPOSITE_TEST;1;TEST @Value(mode_id) = 3'1'FME_NUM_CONDITIONS2___
      SET_TO mode_4_D-T = FME_CONDITIONAL:DEFAULT_VALUE'0'BOOL_OP;OR;COMPOSITE_TEST;1;TEST @Value(mode_id) = 4'1'FME_NUM_CONDITIONS2___
      SET_TO mode_5_D-T = FME_CONDITIONAL:DEFAULT_VALUE'0'BOOL_OP;OR;COMPOSITE_TEST;1;TEST @Value(mode_id) = 5'1'FME_NUM_CONDITIONS2___
      SET_TO mode_6_D-T = FME_CONDITIONAL:DEFAULT_VALUE'0'BOOL_OP;OR;COMPOSITE_TEST;1;TEST @Value(mode_id) = 6'1'FME_NUM_CONDITIONS2___
      SET_TO mode_7_D-T = FME_CONDITIONAL:DEFAULT_VALUE'0'BOOL_OP;OR;COMPOSITE_TEST;1;TEST @Value(mode_id) = 7'1'FME_NUM_CONDITIONS2___
      SET_TO mode_8_D-T = FME_CONDITIONAL:DEFAULT_VALUE'0'BOOL_OP;OR;COMPOSITE_TEST;1;TEST @Value(mode_id) = 8'1'FME_NUM_CONDITIONS2___
      SET_TO mode_9_D-T = FME_CONDITIONAL:DEFAULT_VALUE'0'BOOL_OP;OR;COMPOSITE_TEST;1;TEST @Value(mode_id) = 9'1'FME_NUM_CONDITIONS2___
      SET_TO mode_10_D-T = FME_CONDITIONAL:DEFAULT_VALUE'0'BOOL_OP;OR;COMPOSITE_TEST;1;TEST @Value(mode_id) = 10'1'FME_NUM_CONDITIONS2___
      SET_TO mode_11_D-T = FME_CONDITIONAL:DEFAULT_VALUE'0'BOOL_OP;OR;COMPOSITE_TEST;1;TEST @Value(mode_id) = 11'1'FME_NUM_CONDITIONS2___
      SET_TO mode_12_D-T = FME_CONDITIONAL:DEFAULT_VALUE'0'BOOL_OP;OR;COMPOSITE_TEST;1;TEST @Value(mode_id) = 12'1'FME_NUM_CONDITIONS2___
      SET_TO mode_13_D-T = FME_CONDITIONAL:DEFAULT_VALUE'0'BOOL_OP;OR;COMPOSITE_TEST;1;TEST @Value(mode_id) = 13'1'FME_NUM_CONDITIONS2___
      SET_TO mode_14_D-T = FME_CONDITIONAL:DEFAULT_VALUE'0'BOOL_OP;OR;COMPOSITE_TEST;1;TEST @Value(mode_id) = 14'1'FME_NUM_CONDITIONS2___
      SET_TO mode_15_D-T = FME_CONDITIONAL:DEFAULT_VALUE'0'BOOL_OP;OR;COMPOSITE_TEST;1;TEST @Value(mode_id) = 15'1'FME_NUM_CONDITIONS2___
      SET_TO mode_16_D-T = FME_CONDITIONAL:DEFAULT_VALUE'0'BOOL_OP;OR;COMPOSITE_TEST;1;TEST @Value(mode_id) = 16'1'FME_NUM_CONDITIONS2___
      SET_TO
    -> Aggregator_2
Aggregator_2
    ACCUM_ATTRS_NAME = Drop Incoming Attributes
    AGGREGATE_TYPE = Homogeneous Collection (If Possible)
    GROUP_BY = societe_id
    MODE = Geometry - Assemble One Level
    SEP = ,
    SUM = mode_1_D-T mode_2_D-T mode_10_D-T mode_11_D-T mode_12_D-T mode_13_D-T mode_14_D-T mode_15_D-T mode_16_D-T mode_3_D-T mode_4_D-T mode_5_D-T mode_6_D-T mode_7_D-T mode_8_D-T mode_9_D-T
    AGGREGATE -> FeatureMerger_22 [SUPPLIER]
FeatureMerger_22
    ATTR_ACCUM_MODE = Merge Supplier
    ATTR_CONFLICT_RES = Use Requestor
    IGNORE_NULLS = No
    JOIN_KEYS = @Value(id_societe) @Value(societe_id) AUTO
    MERGE_TYPE = Attributes Only
    PROCESS_DUPS = NO
    REJECT_NULL_MISSING_KEYS = No
    SUPPLIERS_FIRST = No
    MERGED -> FeatureMerger_23 [REQUESTOR]
    UNMERGED_REQUESTOR -> FeatureMerger_23 [REQUESTOR]
FeatureMerger_54
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    USED_SUPPLIER -> StatisticsCalculator_4
StatisticsCalculator_4
    CALCULATION_MODE = NUMERIC
    FEAT_STATS = utilisateur_id,NUMERIC_MODE,,,COUNT,,,,,,,,,,
    GROUP_BY = societe_id
    SUMMARY -> AttributeRenamer_5
AttributeRenamer_5
    ATTR_TABLE = RENAME_SET_DEFAULT utilisateur_id.total_count > nb_utilisateurs_D-T
    MISSING_INPUT_ATTRS = REMOVE
    -> FeatureMerger_39 [SUPPLIER]
Tester_Motif_defini_Pro_2
    BOOL_OP = OR
    TEST_CLAUSE:
      TEST @Value(motif_defini_id) = 5
      TEST @Value(motif_defini_id) = 8
    TEST_MODE = TEST
    PASSED -> AttributeManager_19
    PASSED -> FeatureMerger_55 [REQUESTOR]
AttributeManager_19
    ATTR_TABLE:
      SET_TO mode_1_Pro = FME_CONDITIONAL:DEFAULT_VALUE'0'BOOL_OP;OR;COMPOSITE_TEST;1;TEST @Value(mode_id) = 1'1'FME_NUM_CONDITIONS2___
      SET_TO mode_2_Pro = FME_CONDITIONAL:DEFAULT_VALUE'0'BOOL_OP;OR;COMPOSITE_TEST;1;TEST @Value(mode_id) = 2'1'FME_NUM_CONDITIONS2___
      SET_TO mode_3_Pro = FME_CONDITIONAL:DEFAULT_VALUE'0'BOOL_OP;OR;COMPOSITE_TEST;1;TEST @Value(mode_id) = 3'1'FME_NUM_CONDITIONS2___
      SET_TO mode_4_Pro = FME_CONDITIONAL:DEFAULT_VALUE'0'BOOL_OP;OR;COMPOSITE_TEST;1;TEST @Value(mode_id) = 4'1'FME_NUM_CONDITIONS2___
      SET_TO mode_5_Pro = FME_CONDITIONAL:DEFAULT_VALUE'0'BOOL_OP;OR;COMPOSITE_TEST;1;TEST @Value(mode_id) = 5'1'FME_NUM_CONDITIONS2___
      SET_TO mode_6_Pro = FME_CONDITIONAL:DEFAULT_VALUE'0'BOOL_OP;OR;COMPOSITE_TEST;1;TEST @Value(mode_id) = 6'1'FME_NUM_CONDITIONS2___
      SET_TO mode_7_Pro = FME_CONDITIONAL:DEFAULT_VALUE'0'BOOL_OP;OR;COMPOSITE_TEST;1;TEST @Value(mode_id) = 7'1'FME_NUM_CONDITIONS2___
      SET_TO mode_8_Pro = FME_CONDITIONAL:DEFAULT_VALUE'0'BOOL_OP;OR;COMPOSITE_TEST;1;TEST @Value(mode_id) = 8'1'FME_NUM_CONDITIONS2___
      SET_TO mode_9_Pro = FME_CONDITIONAL:DEFAULT_VALUE'0'BOOL_OP;OR;COMPOSITE_TEST;1;TEST @Value(mode_id) = 9'1'FME_NUM_CONDITIONS2___
      SET_TO mode_10_Pro = FME_CONDITIONAL:DEFAULT_VALUE'0'BOOL_OP;OR;COMPOSITE_TEST;1;TEST @Value(mode_id) = 10'1'FME_NUM_CONDITIONS2___
      SET_TO mode_11_Pro = FME_CONDITIONAL:DEFAULT_VALUE'0'BOOL_OP;OR;COMPOSITE_TEST;1;TEST @Value(mode_id) = 11'1'FME_NUM_CONDITIONS2___
      SET_TO mode_12_Pro = FME_CONDITIONAL:DEFAULT_VALUE'0'BOOL_OP;OR;COMPOSITE_TEST;1;TEST @Value(mode_id) = 12'1'FME_NUM_CONDITIONS2___
      SET_TO mode_13_Pro = FME_CONDITIONAL:DEFAULT_VALUE'0'BOOL_OP;OR;COMPOSITE_TEST;1;TEST @Value(mode_id) = 13'1'FME_NUM_CONDITIONS2___
      SET_TO mode_14_Pro = FME_CONDITIONAL:DEFAULT_VALUE'0'BOOL_OP;OR;COMPOSITE_TEST;1;TEST @Value(mode_id) = 14'1'FME_NUM_CONDITIONS2___
      SET_TO mode_15_Pro = FME_CONDITIONAL:DEFAULT_VALUE'0'BOOL_OP;OR;COMPOSITE_TEST;1;TEST @Value(mode_id) = 15'1'FME_NUM_CONDITIONS2___
      SET_TO mode_16_Pro = FME_CONDITIONAL:DEFAULT_VALUE'0'BOOL_OP;OR;COMPOSITE_TEST;1;TEST @Value(mode_id) = 16'1'FME_NUM_CONDITIONS2___
      SET_TO
    -> Aggregator_3
Aggregator_3
    ACCUM_ATTRS_NAME = Drop Incoming Attributes
    AGGREGATE_TYPE = Homogeneous Collection (If Possible)
    GROUP_BY = societe_id
    MODE = Geometry - Assemble One Level
    SEP = ,
    SUM = mode_10_Pro mode_11_Pro mode_12_Pro mode_13_Pro mode_14_Pro mode_15_Pro mode_16_Pro mode_1_Pro mode_2_Pro mode_3_Pro mode_4_Pro mode_5_Pro mode_6_Pro mode_7_Pro mode_8_Pro mode_9_Pro
    AGGREGATE -> FeatureMerger_23 [SUPPLIER]
FeatureMerger_23
    ATTR_ACCUM_MODE = Merge Supplier
    ATTR_CONFLICT_RES = Use Requestor
    IGNORE_NULLS = No
    JOIN_KEYS = @Value(id_societe) @Value(societe_id) AUTO
    MERGE_TYPE = Attributes Only
    PROCESS_DUPS = NO
    REJECT_NULL_MISSING_KEYS = No
    SUPPLIERS_FIRST = No
    MERGED -> FeatureMerger_39 [REQUESTOR]
    UNMERGED_REQUESTOR -> FeatureMerger_39 [REQUESTOR]
FeatureMerger_39
    ATTR_ACCUM_MODE = Merge Supplier
    ATTR_CONFLICT_RES = Use Requestor
    IGNORE_NULLS = No
    JOIN_KEYS = @Value(id_societe) @Value(societe_id) AUTO
    MERGE_TYPE = Attributes Only
    PROCESS_DUPS = NO
    REJECT_NULL_MISSING_KEYS = No
    SUPPLIERS_FIRST = No
    MERGED -> FeatureMerger_56 [REQUESTOR]
    UNMERGED_REQUESTOR -> FeatureMerger_56 [REQUESTOR]
FeatureMerger_55
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    USED_SUPPLIER -> StatisticsCalculator_18
StatisticsCalculator_18
    CALCULATION_MODE = NUMERIC
    FEAT_STATS = utilisateur_id,NUMERIC_MODE,,,COUNT,,,,,,,,,,
    GROUP_BY = societe_id
    SUMMARY -> AttributeRenamer_6
AttributeRenamer_6
    ATTR_TABLE = RENAME_SET_DEFAULT utilisateur_id.total_count > nb_utilisateurs_pro
    MISSING_INPUT_ATTRS = REMOVE
    -> FeatureMerger_56 [SUPPLIER]
FeatureMerger_56
    ATTR_ACCUM_MODE = Merge Supplier
    ATTR_CONFLICT_RES = Use Requestor
    IGNORE_NULLS = No
    JOIN_KEYS = @Value(id_societe) @Value(societe_id) AUTO
    MERGE_TYPE = Attributes Only
    PROCESS_DUPS = NO
    REJECT_NULL_MISSING_KEYS = No
    SUPPLIERS_FIRST = No
    MERGED -> Sorter_4
    UNMERGED_REQUESTOR -> Sorter_4
Sorter_4
    SORT_PARM = id_societe NATURAL ASCENDING
    SORTED -> Statistiques_Mode_Societes (writer XLSXW_2)
Statistiques_Mode_Societes (writer XLSXW_2)
    attributes: id_societe number(20), nom_societe string(100), mode_1_D-T string(200), mode_2_D-T string(200), mode_3_D-T string(200), mode_4_D-T string(200), mode_5_D-T string(200), mode_6_D-T string(200), mode_7_D-T string(200), mode_8_D-T string(200), mode_9_D-T string(200), mode_10_D-T string(200), mode_11_D-T string(200), mode_12_D-T string(200), mode_13_D-T string(200), mode_14_D-T string(200), mode_15_D-T string(200), mode_16_D-T string(200), mode_1_Pro string(200), mode_2_Pro string(200), mode_3_Pro string(200), mode_4_Pro string(200), mode_5_Pro string(200), mode_6_Pro string(200), mode_7_Pro string(200), mode_8_Pro string(200), mode_9_Pro string(200), mode_10_Pro string(200), mode_11_Pro string(200), mode_12_Pro string(200),
      mode_13_Pro string(200), mode_14_Pro string(200), mode_15_Pro string(200), mode_16_Pro string(200), nb_utilisateurs_D-T number(20), nb_utilisateurs_pro number(20)

Bookmark: Statistiques modes par site, nombre de déplacements
Note: public.deplacements_site
Junction_18
    -> FeatureMerger_25 [REQUESTOR]
Tester_Motif_defini_D-T_3
    BOOL_OP = OR
    TEST_CLAUSE:
      TEST @Value(motif_defini_id) = 1
      TEST @Value(motif_defini_id) = 2
      TEST @Value(motif_defini_id) = 3
      TEST @Value(motif_defini_id) = 4
      TEST @Value(motif_defini_id) = 6
      TEST @Value(motif_defini_id) = 7
    TEST_MODE = TEST
    PASSED -> AttributeManager_22
    PASSED -> FeatureMerger_57 [REQUESTOR]
AttributeManager_22
    ATTR_TABLE:
      SET_TO mode_1_D-T = FME_CONDITIONAL:DEFAULT_VALUE'0'BOOL_OP;OR;COMPOSITE_TEST;1;TEST @Value(mode_id) = 1'1'FME_NUM_CONDITIONS2___
      SET_TO mode_2_D-T = FME_CONDITIONAL:DEFAULT_VALUE'0'BOOL_OP;OR;COMPOSITE_TEST;1;TEST @Value(mode_id) = 2'1'FME_NUM_CONDITIONS2___
      SET_TO mode_3_D-T = FME_CONDITIONAL:DEFAULT_VALUE'0'BOOL_OP;OR;COMPOSITE_TEST;1;TEST @Value(mode_id) = 3'1'FME_NUM_CONDITIONS2___
      SET_TO mode_4_D-T = FME_CONDITIONAL:DEFAULT_VALUE'0'BOOL_OP;OR;COMPOSITE_TEST;1;TEST @Value(mode_id) = 4'1'FME_NUM_CONDITIONS2___
      SET_TO mode_5_D-T = FME_CONDITIONAL:DEFAULT_VALUE'0'BOOL_OP;OR;COMPOSITE_TEST;1;TEST @Value(mode_id) = 5'1'FME_NUM_CONDITIONS2___
      SET_TO mode_6_D-T = FME_CONDITIONAL:DEFAULT_VALUE'0'BOOL_OP;OR;COMPOSITE_TEST;1;TEST @Value(mode_id) = 6'1'FME_NUM_CONDITIONS2___
      SET_TO mode_7_D-T = FME_CONDITIONAL:DEFAULT_VALUE'0'BOOL_OP;OR;COMPOSITE_TEST;1;TEST @Value(mode_id) = 7'1'FME_NUM_CONDITIONS2___
      SET_TO mode_8_D-T = FME_CONDITIONAL:DEFAULT_VALUE'0'BOOL_OP;OR;COMPOSITE_TEST;1;TEST @Value(mode_id) = 8'1'FME_NUM_CONDITIONS2___
      SET_TO mode_9_D-T = FME_CONDITIONAL:DEFAULT_VALUE'0'BOOL_OP;OR;COMPOSITE_TEST;1;TEST @Value(mode_id) = 9'1'FME_NUM_CONDITIONS2___
      SET_TO mode_10_D-T = FME_CONDITIONAL:DEFAULT_VALUE'0'BOOL_OP;OR;COMPOSITE_TEST;1;TEST @Value(mode_id) = 10'1'FME_NUM_CONDITIONS2___
      SET_TO mode_11_D-T = FME_CONDITIONAL:DEFAULT_VALUE'0'BOOL_OP;OR;COMPOSITE_TEST;1;TEST @Value(mode_id) = 11'1'FME_NUM_CONDITIONS2___
      SET_TO mode_12_D-T = FME_CONDITIONAL:DEFAULT_VALUE'0'BOOL_OP;OR;COMPOSITE_TEST;1;TEST @Value(mode_id) = 12'1'FME_NUM_CONDITIONS2___
      SET_TO mode_13_D-T = FME_CONDITIONAL:DEFAULT_VALUE'0'BOOL_OP;OR;COMPOSITE_TEST;1;TEST @Value(mode_id) = 13'1'FME_NUM_CONDITIONS2___
      SET_TO mode_14_D-T = FME_CONDITIONAL:DEFAULT_VALUE'0'BOOL_OP;OR;COMPOSITE_TEST;1;TEST @Value(mode_id) = 14'1'FME_NUM_CONDITIONS2___
      SET_TO mode_15_D-T = FME_CONDITIONAL:DEFAULT_VALUE'0'BOOL_OP;OR;COMPOSITE_TEST;1;TEST @Value(mode_id) = 15'1'FME_NUM_CONDITIONS2___
      SET_TO mode_16_D-T = FME_CONDITIONAL:DEFAULT_VALUE'0'BOOL_OP;OR;COMPOSITE_TEST;1;TEST @Value(mode_id) = 16'1'FME_NUM_CONDITIONS2___
      SET_TO
    -> Aggregator_5
Aggregator_5
    ACCUM_ATTRS_NAME = Drop Incoming Attributes
    AGGREGATE_TYPE = Homogeneous Collection (If Possible)
    GROUP_BY = site_id
    MODE = Geometry - Assemble One Level
    SEP = ,
    SUM = mode_1_D-T mode_2_D-T mode_10_D-T mode_11_D-T mode_12_D-T mode_13_D-T mode_14_D-T mode_15_D-T mode_16_D-T mode_3_D-T mode_4_D-T mode_5_D-T mode_6_D-T mode_7_D-T mode_8_D-T mode_9_D-T
    AGGREGATE -> FeatureMerger_25 [SUPPLIER]
FeatureMerger_25
    ATTR_ACCUM_MODE = Merge Supplier
    ATTR_CONFLICT_RES = Use Requestor
    IGNORE_NULLS = No
    JOIN_KEYS = @Value(id_site) @Value(site_id) AUTO
    MERGE_TYPE = Attributes Only
    PROCESS_DUPS = NO
    REJECT_NULL_MISSING_KEYS = No
    SUPPLIERS_FIRST = No
    MERGED -> FeatureMerger_26 [REQUESTOR]
    UNMERGED_REQUESTOR -> FeatureMerger_26 [REQUESTOR]
FeatureMerger_57
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    USED_SUPPLIER -> StatisticsCalculator_5
StatisticsCalculator_5
    CALCULATION_MODE = NUMERIC
    FEAT_STATS = utilisateur_id,NUMERIC_MODE,,,COUNT,,,,,,,,,,
    GROUP_BY = site_id
    SUMMARY -> AttributeRenamer_7
AttributeRenamer_7
    ATTR_TABLE = RENAME_SET_DEFAULT utilisateur_id.total_count > nb_utilisateurs_D-T
    MISSING_INPUT_ATTRS = REMOVE
    -> FeatureMerger_40 [SUPPLIER]
Tester_Motif_defini_Pro_3
    BOOL_OP = OR
    TEST_CLAUSE:
      TEST @Value(motif_defini_id) = 5
      TEST @Value(motif_defini_id) = 8
    TEST_MODE = TEST
    PASSED -> AttributeManager_23
    PASSED -> FeatureMerger_58 [REQUESTOR]
AttributeManager_23
    ATTR_TABLE:
      SET_TO mode_1_Pro = FME_CONDITIONAL:DEFAULT_VALUE'0'BOOL_OP;OR;COMPOSITE_TEST;1;TEST @Value(mode_id) = 1'1'FME_NUM_CONDITIONS2___
      SET_TO mode_2_Pro = FME_CONDITIONAL:DEFAULT_VALUE'0'BOOL_OP;OR;COMPOSITE_TEST;1;TEST @Value(mode_id) = 2'1'FME_NUM_CONDITIONS2___
      SET_TO mode_3_Pro = FME_CONDITIONAL:DEFAULT_VALUE'0'BOOL_OP;OR;COMPOSITE_TEST;1;TEST @Value(mode_id) = 3'1'FME_NUM_CONDITIONS2___
      SET_TO mode_4_Pro = FME_CONDITIONAL:DEFAULT_VALUE'0'BOOL_OP;OR;COMPOSITE_TEST;1;TEST @Value(mode_id) = 4'1'FME_NUM_CONDITIONS2___
      SET_TO mode_5_Pro = FME_CONDITIONAL:DEFAULT_VALUE'0'BOOL_OP;OR;COMPOSITE_TEST;1;TEST @Value(mode_id) = 5'1'FME_NUM_CONDITIONS2___
      SET_TO mode_6_Pro = FME_CONDITIONAL:DEFAULT_VALUE'0'BOOL_OP;OR;COMPOSITE_TEST;1;TEST @Value(mode_id) = 6'1'FME_NUM_CONDITIONS2___
      SET_TO mode_7_Pro = FME_CONDITIONAL:DEFAULT_VALUE'0'BOOL_OP;OR;COMPOSITE_TEST;1;TEST @Value(mode_id) = 7'1'FME_NUM_CONDITIONS2___
      SET_TO mode_8_Pro = FME_CONDITIONAL:DEFAULT_VALUE'0'BOOL_OP;OR;COMPOSITE_TEST;1;TEST @Value(mode_id) = 8'1'FME_NUM_CONDITIONS2___
      SET_TO mode_9_Pro = FME_CONDITIONAL:DEFAULT_VALUE'0'BOOL_OP;OR;COMPOSITE_TEST;1;TEST @Value(mode_id) = 9'1'FME_NUM_CONDITIONS2___
      SET_TO mode_10_Pro = FME_CONDITIONAL:DEFAULT_VALUE'0'BOOL_OP;OR;COMPOSITE_TEST;1;TEST @Value(mode_id) = 10'1'FME_NUM_CONDITIONS2___
      SET_TO mode_11_Pro = FME_CONDITIONAL:DEFAULT_VALUE'0'BOOL_OP;OR;COMPOSITE_TEST;1;TEST @Value(mode_id) = 11'1'FME_NUM_CONDITIONS2___
      SET_TO mode_12_Pro = FME_CONDITIONAL:DEFAULT_VALUE'0'BOOL_OP;OR;COMPOSITE_TEST;1;TEST @Value(mode_id) = 12'1'FME_NUM_CONDITIONS2___
      SET_TO mode_13_Pro = FME_CONDITIONAL:DEFAULT_VALUE'0'BOOL_OP;OR;COMPOSITE_TEST;1;TEST @Value(mode_id) = 13'1'FME_NUM_CONDITIONS2___
      SET_TO mode_14_Pro = FME_CONDITIONAL:DEFAULT_VALUE'0'BOOL_OP;OR;COMPOSITE_TEST;1;TEST @Value(mode_id) = 14'1'FME_NUM_CONDITIONS2___
      SET_TO mode_15_Pro = FME_CONDITIONAL:DEFAULT_VALUE'0'BOOL_OP;OR;COMPOSITE_TEST;1;TEST @Value(mode_id) = 15'1'FME_NUM_CONDITIONS2___
      SET_TO mode_16_Pro = FME_CONDITIONAL:DEFAULT_VALUE'0'BOOL_OP;OR;COMPOSITE_TEST;1;TEST @Value(mode_id) = 16'1'FME_NUM_CONDITIONS2___
      SET_TO
    -> Aggregator_6
Aggregator_6
    ACCUM_ATTRS_NAME = Drop Incoming Attributes
    AGGREGATE_TYPE = Homogeneous Collection (If Possible)
    GROUP_BY = site_id
    MODE = Geometry - Assemble One Level
    SEP = ,
    SUM = mode_10_Pro mode_11_Pro mode_12_Pro mode_13_Pro mode_14_Pro mode_15_Pro mode_16_Pro mode_1_Pro mode_2_Pro mode_3_Pro mode_4_Pro mode_5_Pro mode_6_Pro mode_7_Pro mode_8_Pro mode_9_Pro
    AGGREGATE -> FeatureMerger_26 [SUPPLIER]
FeatureMerger_26
    ATTR_ACCUM_MODE = Merge Supplier
    ATTR_CONFLICT_RES = Use Requestor
    IGNORE_NULLS = No
    JOIN_KEYS = @Value(id_site) @Value(site_id) AUTO
    MERGE_TYPE = Attributes Only
    PROCESS_DUPS = NO
    REJECT_NULL_MISSING_KEYS = No
    SUPPLIERS_FIRST = No
    MERGED -> FeatureMerger_40 [REQUESTOR]
    UNMERGED_REQUESTOR -> FeatureMerger_40 [REQUESTOR]
FeatureMerger_40
    ATTR_ACCUM_MODE = Merge Supplier
    ATTR_CONFLICT_RES = Use Requestor
    IGNORE_NULLS = No
    JOIN_KEYS = @Value(id_site) @Value(site_id) AUTO
    MERGE_TYPE = Attributes Only
    PROCESS_DUPS = NO
    REJECT_NULL_MISSING_KEYS = No
    SUPPLIERS_FIRST = No
    MERGED -> FeatureMerger_59 [REQUESTOR]
    UNMERGED_REQUESTOR -> FeatureMerger_59 [REQUESTOR]
FeatureMerger_58
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    USED_SUPPLIER -> StatisticsCalculator_19
StatisticsCalculator_19
    CALCULATION_MODE = NUMERIC
    FEAT_STATS = utilisateur_id,NUMERIC_MODE,,,COUNT,,,,,,,,,,
    GROUP_BY = site_id
    SUMMARY -> AttributeRenamer_8
AttributeRenamer_8
    ATTR_TABLE = RENAME_SET_DEFAULT utilisateur_id.total_count > nb_utilisateurs_pro
    MISSING_INPUT_ATTRS = REMOVE
    -> FeatureMerger_59 [SUPPLIER]
FeatureMerger_59
    ATTR_ACCUM_MODE = Merge Supplier
    ATTR_CONFLICT_RES = Use Requestor
    IGNORE_NULLS = No
    JOIN_KEYS = @Value(id_site) @Value(site_id) AUTO
    MERGE_TYPE = Attributes Only
    PROCESS_DUPS = NO
    REJECT_NULL_MISSING_KEYS = No
    SUPPLIERS_FIRST = No
    MERGED -> Sorter_3
    UNMERGED_REQUESTOR -> Sorter_3
Sorter_3
    SORT_PARM = id_site NATURAL ASCENDING
    SORTED -> Statistiques_Mode_Sites (writer XLSXW_2)
Statistiques_Mode_Sites (writer XLSXW_2)
    attributes: id_site number(20), nom_site string(100), mode_1_D-T string(200), mode_2_D-T string(200), mode_3_D-T string(200), mode_4_D-T string(200), mode_5_D-T string(200), mode_6_D-T string(200), mode_7_D-T string(200), mode_8_D-T string(200), mode_9_D-T string(200), mode_10_D-T string(200), mode_11_D-T string(200), mode_12_D-T string(200), mode_13_D-T string(200), mode_14_D-T string(200), mode_15_D-T string(200), mode_16_D-T string(200), mode_1_Pro string(200), mode_2_Pro string(200), mode_3_Pro string(200), mode_4_Pro string(200), mode_5_Pro string(200), mode_6_Pro string(200), mode_7_Pro string(200), mode_8_Pro string(200), mode_9_Pro string(200), mode_10_Pro string(200), mode_11_Pro string(200), mode_12_Pro string(200),
      mode_13_Pro string(200), mode_14_Pro string(200), mode_15_Pro string(200), mode_16_Pro string(200), nb_utilisateurs_D-T number(20), nb_utilisateurs_pro number(20)

Bookmark: Statistiques modes par site, nombre de kilomètres
Note: public.deplacements_site
Junction_14
    -> FeatureMerger_42 [REQUESTOR]
Note: FeatureMerger_16 : Merged
Junction_26
    -> FeatureMerger_61 [SUPPLIER]
Note: FeatureMerger_16 : Merged
Junction_24
    -> FeatureMerger_60 [SUPPLIER]
Tester_Motif_defini_D-T_7
    BOOL_OP = OR
    TEST_CLAUSE:
      TEST @Value(motif_defini_id) = 1
      TEST @Value(motif_defini_id) = 2
      TEST @Value(motif_defini_id) = 3
      TEST @Value(motif_defini_id) = 4
      TEST @Value(motif_defini_id) = 6
      TEST @Value(motif_defini_id) = 7
    TEST_MODE = TEST
    PASSED -> AttributeManager_13
    PASSED -> StatisticsCalculator_16
    PASSED -> FeatureMerger_60 [REQUESTOR]
AttributeManager_13
    ATTR_TABLE:
      SET_TO mode_1_D-T = FME_CONDITIONAL:DEFAULT_VALUE'0'BOOL_OP;OR;COMPOSITE_TEST;1;TEST @Value(mode_id) = 1'@Value(distance_voiture_km)'FME_NUM_CONDITIONS2___
      SET_TO mode_2_D-T = FME_CONDITIONAL:DEFAULT_VALUE'0'BOOL_OP;OR;COMPOSITE_TEST;1;TEST @Value(mode_id) = 2'@Value(distance_voiture_km)'FME_NUM_CONDITIONS2___
      SET_TO mode_3_D-T = FME_CONDITIONAL:DEFAULT_VALUE'0'BOOL_OP;OR;COMPOSITE_TEST;1;TEST @Value(mode_id) = 3'@Value(distance_voiture_km)'FME_NUM_CONDITIONS2___
      SET_TO mode_4_D-T = FME_CONDITIONAL:DEFAULT_VALUE'0'BOOL_OP;OR;COMPOSITE_TEST;1;TEST @Value(mode_id) = 4'@Value(distance_voiture_km)'FME_NUM_CONDITIONS2___
      SET_TO mode_5_D-T = FME_CONDITIONAL:DEFAULT_VALUE'0'BOOL_OP;OR;COMPOSITE_TEST;1;TEST @Value(mode_id) = 5'@Value(distance_voiture_km)'FME_NUM_CONDITIONS2___
      SET_TO mode_6_D-T = FME_CONDITIONAL:DEFAULT_VALUE'0'BOOL_OP;OR;COMPOSITE_TEST;1;TEST @Value(mode_id) = 6'@Value(distance_voiture_km)'FME_NUM_CONDITIONS2___
      SET_TO mode_7_D-T = FME_CONDITIONAL:DEFAULT_VALUE'0'BOOL_OP;OR;COMPOSITE_TEST;1;TEST @Value(mode_id) = 7'@Value(distance_velo_km)'FME_NUM_CONDITIONS2___
      SET_TO mode_8_D-T = FME_CONDITIONAL:DEFAULT_VALUE'0'BOOL_OP;OR;COMPOSITE_TEST;1;TEST @Value(mode_id) = 8'@Value(distance_voiture_km)'FME_NUM_CONDITIONS2___
      SET_TO mode_9_D-T = FME_CONDITIONAL:DEFAULT_VALUE'0'BOOL_OP;OR;COMPOSITE_TEST;1;TEST @Value(mode_id) = 9'@Value(distance_voiture_km)'FME_NUM_CONDITIONS2___
      SET_TO mode_10_D-T = FME_CONDITIONAL:DEFAULT_VALUE'0'BOOL_OP;OR;COMPOSITE_TEST;1;TEST @Value(mode_id) = 10'@Value(distance_voiture_km)'FME_NUM_CONDITIONS2___
      SET_TO mode_11_D-T = FME_CONDITIONAL:DEFAULT_VALUE'0'BOOL_OP;OR;COMPOSITE_TEST;1;TEST @Value(mode_id) = 11'@Value(distance_marche_km)'FME_NUM_CONDITIONS2___
      SET_TO mode_12_D-T = FME_CONDITIONAL:DEFAULT_VALUE'0'BOOL_OP;OR;COMPOSITE_TEST;1;TEST @Value(mode_id) = 12'@Value(distance_marche_km)'FME_NUM_CONDITIONS2___
      SET_TO mode_13_D-T = FME_CONDITIONAL:DEFAULT_VALUE'0'BOOL_OP;OR;COMPOSITE_TEST;1;TEST @Value(mode_id) = 13'@Value(distance_voiture_km)'FME_NUM_CONDITIONS2___
      SET_TO mode_14_D-T = FME_CONDITIONAL:DEFAULT_VALUE'_FME_NO_OP_'BOOL_OP;OR;COMPOSITE_TEST;1;TEST @Value(mode_id) = 14'@Value(distance_voiture_km)'FME_NUM_CONDITIONS2___
      SET_TO mode_15_D-T = FME_CONDITIONAL:DEFAULT_VALUE'0'BOOL_OP;OR;COMPOSITE_TEST;1;TEST @Value(mode_id) = 15'@Value(distance_voiture_km)'FME_NUM_CONDITIONS2___
      SET_TO mode_16_D-T = FME_CONDITIONAL:DEFAULT_VALUE'0'BOOL_OP;OR;COMPOSITE_TEST;1;TEST @Value(mode_id) = 16'@Value(distance_voiture_km)'FME_NUM_CONDITIONS2___
      SET_TO
    -> Aggregator_10
Aggregator_10
    ACCUM_ATTRS_NAME = Drop Incoming Attributes
    AGGREGATE_TYPE = Homogeneous Collection (If Possible)
    GROUP_BY = site_id
    MODE = Geometry - Assemble One Level
    SEP = ,
    SUM = mode_1_D-T mode_2_D-T mode_10_D-T mode_11_D-T mode_12_D-T mode_13_D-T mode_14_D-T mode_15_D-T mode_16_D-T mode_3_D-T mode_4_D-T mode_5_D-T mode_6_D-T mode_7_D-T mode_8_D-T mode_9_D-T
    AGGREGATE -> FeatureMerger_42 [SUPPLIER]
FeatureMerger_42
    ATTR_ACCUM_MODE = Merge Supplier
    ATTR_CONFLICT_RES = Use Requestor
    IGNORE_NULLS = No
    JOIN_KEYS = @Value(id_site) @Value(site_id) AUTO
    MERGE_TYPE = Attributes Only
    PROCESS_DUPS = NO
    REJECT_NULL_MISSING_KEYS = No
    SUPPLIERS_FIRST = No
    MERGED -> FeatureMerger_43 [REQUESTOR]
    UNMERGED_REQUESTOR -> FeatureMerger_43 [REQUESTOR]
StatisticsCalculator_16
    CALCULATION_MODE = NUMERIC
    FEAT_STATS = id_deplacement,NUMERIC_MODE,,,COUNT,,,,,,,,,,
    GROUP_BY = site_id
    SUMMARY -> AttributeRenamer_3
AttributeRenamer_3
    ATTR_TABLE = RENAME_SET_DEFAULT id_deplacement.total_count > nb_depl_pendulaires
    MISSING_INPUT_ATTRS = REMOVE
    -> FeatureMerger_52 [REQUESTOR]
FeatureMerger_60
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    USED_SUPPLIER -> StatisticsCalculator_3
StatisticsCalculator_3
    CALCULATION_MODE = NUMERIC
    FEAT_STATS = utilisateur_id,NUMERIC_MODE,,,COUNT,,,,,,,,,,
    GROUP_BY = site_id
    SUMMARY -> AttributeRenamer_11
AttributeRenamer_11
    ATTR_TABLE = RENAME_SET_DEFAULT utilisateur_id.total_count > nb_utilisateurs_D-T
    MISSING_INPUT_ATTRS = REMOVE
    -> FeatureMerger_53 [SUPPLIER]
Tester_Motif_defini_Pro_7
    BOOL_OP = OR
    TEST_CLAUSE:
      TEST @Value(motif_defini_id) = 5
      TEST @Value(motif_defini_id) = 8
    TEST_MODE = TEST
    PASSED -> AttributeManager_28
    PASSED -> StatisticsCalculator_17
    PASSED -> FeatureMerger_61 [REQUESTOR]
AttributeManager_28
    ATTR_TABLE:
      SET_TO mode_1_Pro = FME_CONDITIONAL:DEFAULT_VALUE'0'BOOL_OP;OR;COMPOSITE_TEST;1;TEST @Value(mode_id) = 1'@Value(distance_voiture_km)'FME_NUM_CONDITIONS2___
      SET_TO mode_2_Pro = FME_CONDITIONAL:DEFAULT_VALUE'0'BOOL_OP;OR;COMPOSITE_TEST;1;TEST @Value(mode_id) = 2'@Value(distance_voiture_km)'FME_NUM_CONDITIONS2___
      SET_TO mode_3_Pro = FME_CONDITIONAL:DEFAULT_VALUE'0'BOOL_OP;OR;COMPOSITE_TEST;1;TEST @Value(mode_id) = 3'@Value(distance_voiture_km)'FME_NUM_CONDITIONS2___
      SET_TO mode_4_Pro = FME_CONDITIONAL:DEFAULT_VALUE'0'BOOL_OP;OR;COMPOSITE_TEST;1;TEST @Value(mode_id) = 4'@Value(distance_voiture_km)'FME_NUM_CONDITIONS2___
      SET_TO mode_5_Pro = FME_CONDITIONAL:DEFAULT_VALUE'0'BOOL_OP;OR;COMPOSITE_TEST;1;TEST @Value(mode_id) = 5'@Value(distance_voiture_km)'FME_NUM_CONDITIONS2___
      SET_TO mode_6_Pro = FME_CONDITIONAL:DEFAULT_VALUE'0'BOOL_OP;OR;COMPOSITE_TEST;1;TEST @Value(mode_id) = 6'@Value(distance_voiture_km)'FME_NUM_CONDITIONS2___
      SET_TO mode_7_Pro = FME_CONDITIONAL:DEFAULT_VALUE'0'BOOL_OP;OR;COMPOSITE_TEST;1;TEST @Value(mode_id) = 7'@Value(distance_velo_km)'FME_NUM_CONDITIONS2___
      SET_TO mode_8_Pro = FME_CONDITIONAL:DEFAULT_VALUE'0'BOOL_OP;OR;COMPOSITE_TEST;1;TEST @Value(mode_id) = 8'@Value(distance_voiture_km)'FME_NUM_CONDITIONS2___
      SET_TO mode_9_Pro = FME_CONDITIONAL:DEFAULT_VALUE'0'BOOL_OP;OR;COMPOSITE_TEST;1;TEST @Value(mode_id) = 9'@Value(distance_voiture_km)'FME_NUM_CONDITIONS2___
      SET_TO mode_10_Pro = FME_CONDITIONAL:DEFAULT_VALUE'0'BOOL_OP;OR;COMPOSITE_TEST;1;TEST @Value(mode_id) = 10'@Value(distance_voiture_km)'FME_NUM_CONDITIONS2___
      SET_TO mode_11_Pro = FME_CONDITIONAL:DEFAULT_VALUE'0'BOOL_OP;OR;COMPOSITE_TEST;1;TEST @Value(mode_id) = 11'@Value(distance_marche_km)'FME_NUM_CONDITIONS2___
      SET_TO mode_12_Pro = FME_CONDITIONAL:DEFAULT_VALUE'0'BOOL_OP;OR;COMPOSITE_TEST;1;TEST @Value(mode_id) = 12'@Value(distance_marche_km)'FME_NUM_CONDITIONS2___
      SET_TO mode_13_Pro = FME_CONDITIONAL:DEFAULT_VALUE'0'BOOL_OP;OR;COMPOSITE_TEST;1;TEST @Value(mode_id) = 13'@Value(distance_voiture_km)'FME_NUM_CONDITIONS2___
      SET_TO mode_14_Pro = FME_CONDITIONAL:DEFAULT_VALUE'0'BOOL_OP;OR;COMPOSITE_TEST;1;TEST @Value(mode_id) = 14'@Value(distance_voiture_km)'FME_NUM_CONDITIONS2___
      SET_TO mode_15_Pro = FME_CONDITIONAL:DEFAULT_VALUE'0'BOOL_OP;OR;COMPOSITE_TEST;1;TEST @Value(mode_id) = 15'@Value(distance_voiture_km)'FME_NUM_CONDITIONS2___
      SET_TO mode_16_Pro = FME_CONDITIONAL:DEFAULT_VALUE'0'BOOL_OP;OR;COMPOSITE_TEST;1;TEST @Value(mode_id) = 16'@Value(distance_voiture_km)'FME_NUM_CONDITIONS2___
      SET_TO
    -> Aggregator_11
Aggregator_11
    ACCUM_ATTRS_NAME = Drop Incoming Attributes
    AGGREGATE_TYPE = Homogeneous Collection (If Possible)
    GROUP_BY = site_id
    MODE = Geometry - Assemble One Level
    SEP = ,
    SUM = mode_10_Pro mode_11_Pro mode_12_Pro mode_13_Pro mode_14_Pro mode_15_Pro mode_16_Pro mode_1_Pro mode_2_Pro mode_3_Pro mode_4_Pro mode_5_Pro mode_6_Pro mode_7_Pro mode_8_Pro mode_9_Pro
    AGGREGATE -> FeatureMerger_43 [SUPPLIER]
FeatureMerger_43
    ATTR_ACCUM_MODE = Merge Supplier
    ATTR_CONFLICT_RES = Use Requestor
    IGNORE_NULLS = No
    JOIN_KEYS = @Value(id_site) @Value(site_id) AUTO
    MERGE_TYPE = Attributes Only
    PROCESS_DUPS = NO
    REJECT_NULL_MISSING_KEYS = No
    SUPPLIERS_FIRST = No
    MERGED -> FeatureMerger_47 [REQUESTOR]
    UNMERGED_REQUESTOR -> FeatureMerger_47 [REQUESTOR]
StatisticsCalculator_17
    CALCULATION_MODE = NUMERIC
    FEAT_STATS = id_deplacement,NUMERIC_MODE,,,COUNT,,,,,,,,,,
    GROUP_BY = site_id
    SUMMARY -> AttributeRenamer_4
AttributeRenamer_4
    ATTR_TABLE = RENAME_SET_DEFAULT id_deplacement.total_count > nb_depl_pro
    MISSING_INPUT_ATTRS = REMOVE
    -> FeatureMerger_52 [SUPPLIER]
FeatureMerger_52
    ATTR_ACCUM_MODE = Merge Supplier
    ATTR_CONFLICT_RES = Use Requestor
    IGNORE_NULLS = No
    JOIN_KEYS = @Value(site_id) @Value(site_id) AUTO
    MERGE_TYPE = Attributes Only
    PROCESS_DUPS = NO
    REJECT_NULL_MISSING_KEYS = No
    SUPPLIERS_FIRST = No
    MERGED -> FeatureMerger_53 [REQUESTOR]
    UNMERGED_REQUESTOR -> FeatureMerger_53 [REQUESTOR]
FeatureMerger_53
    ATTR_ACCUM_MODE = Merge Supplier
    ATTR_CONFLICT_RES = Use Requestor
    IGNORE_NULLS = No
    JOIN_KEYS = @Value(site_id) @Value(site_id) AUTO
    MERGE_TYPE = Attributes Only
    PROCESS_DUPS = NO
    REJECT_NULL_MISSING_KEYS = No
    SUPPLIERS_FIRST = No
    MERGED -> FeatureMerger_62 [REQUESTOR]
FeatureMerger_61
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    USED_SUPPLIER -> StatisticsCalculator_10
StatisticsCalculator_10
    CALCULATION_MODE = NUMERIC
    FEAT_STATS = utilisateur_id,NUMERIC_MODE,,,COUNT,,,,,,,,,,
    GROUP_BY = site_id
    SUMMARY -> AttributeRenamer_12
AttributeRenamer_12
    ATTR_TABLE = RENAME_SET_DEFAULT utilisateur_id.total_count > nb_utilisateurs_pro
    MISSING_INPUT_ATTRS = REMOVE
    -> FeatureMerger_62 [SUPPLIER]
FeatureMerger_62
    ATTR_ACCUM_MODE = Merge Supplier
    ATTR_CONFLICT_RES = Use Requestor
    IGNORE_NULLS = No
    JOIN_KEYS = @Value(site_id) @Value(site_id) AUTO
    MERGE_TYPE = Attributes Only
    PROCESS_DUPS = NO
    REJECT_NULL_MISSING_KEYS = No
    SUPPLIERS_FIRST = No
    MERGED -> FeatureMerger_47 [SUPPLIER]
    UNMERGED_REQUESTOR -> FeatureMerger_47 [SUPPLIER]
FeatureMerger_47
    ATTR_ACCUM_MODE = Merge Supplier
    ATTR_CONFLICT_RES = Use Requestor
    IGNORE_NULLS = No
    JOIN_KEYS = @Value(id_site) @Value(site_id) AUTO
    MERGE_TYPE = Attributes Only
    PROCESS_DUPS = NO
    REJECT_NULL_MISSING_KEYS = No
    SUPPLIERS_FIRST = No
    MERGED -> AttributeManager_10
    UNMERGED_REQUESTOR -> AttributeManager_10
AttributeManager_10
    ATTR_TABLE:
      SET_TO mode_1_D-T = @Evaluate(@round(@Value(mode_1_D-T),0))
      SET_TO mode_2_D-T = @Evaluate(@round(@Value(mode_2_D-T),0))
      SET_TO mode_3_D-T = @Evaluate(@round(@Value(mode_3_D-T),0))
      SET_TO mode_4_D-T = @Evaluate(@round(@Value(mode_4_D-T),0))
      SET_TO mode_5_D-T = @Evaluate(@round(@Value(mode_5_D-T),0))
      SET_TO mode_6_D-T = @Evaluate(@round(@Value(mode_6_D-T),0))
      SET_TO mode_7_D-T = @Evaluate(@round(@Value(mode_7_D-T),0))
      SET_TO mode_8_D-T = @Evaluate(@round(@Value(mode_8_D-T),0))
      SET_TO mode_9_D-T = @Evaluate(@round(@Value(mode_9_D-T),0))
      SET_TO mode_10_D-T = @Evaluate(@round(@Value(mode_10_D-T),0))
      SET_TO mode_11_D-T = @Evaluate(@round(@Value(mode_11_D-T),0))
      SET_TO mode_12_D-T = @Evaluate(@round(@Value(mode_12_D-T),0))
      SET_TO mode_13_D-T = @Evaluate(@round(@Value(mode_13_D-T),0))
      SET_TO mode_14_D-T = @Evaluate(@round(@Value(mode_14_D-T),0))
      SET_TO mode_15_D-T = @Evaluate(@round(@Value(mode_15_D-T),0))
      SET_TO mode_16_D-T = @Evaluate(@round(@Value(mode_16_D-T),0))
      SET_TO mode_1_Pro = @Evaluate(@round(@Value(mode_1_Pro),0))
      SET_TO mode_2_Pro = @Evaluate(@round(@Value(mode_2_Pro),0))
      SET_TO mode_3_Pro = @Evaluate(@round(@Value(mode_3_Pro),0))
      SET_TO mode_4_Pro = @Evaluate(@round(@Value(mode_4_Pro),0))
      SET_TO mode_5_Pro = @Evaluate(@round(@Value(mode_5_Pro),0))
      SET_TO mode_6_Pro = @Evaluate(@round(@Value(mode_6_Pro),0))
      SET_TO mode_7_Pro = @Evaluate(@round(@Value(mode_7_Pro),0))
      SET_TO mode_8_Pro = @Evaluate(@round(@Value(mode_8_Pro),0))
      SET_TO mode_9_Pro = @Evaluate(@round(@Value(mode_9_Pro),0))
      SET_TO mode_10_Pro = @Evaluate(@round(@Value(mode_10_Pro),0))
      SET_TO mode_11_Pro = @Evaluate(@round(@Value(mode_11_Pro),0))
      SET_TO mode_12_Pro = @Evaluate(@round(@Value(mode_12_Pro),0))
      SET_TO mode_13_Pro = @Evaluate(@round(@Value(mode_13_Pro),0))
      SET_TO mode_14_Pro = @Evaluate(@round(@Value(mode_14_Pro),0))
      SET_TO mode_15_Pro = @Evaluate(@round(@Value(mode_15_Pro),0))
      SET_TO mode_16_Pro = @Evaluate(@round(@Value(mode_16_Pro),0))
    USER_EXPOSED_ATTRIBUTES = utilisateur_id.total_count
    -> Sorter_14
Sorter_14
    SORT_PARM = id_site NATURAL ASCENDING
    SORTED -> Statistiques_Mode_Sites (writer XLSXW_4)
Statistiques_Mode_Sites (writer XLSXW_4)
    attributes: id_site number(20), nom_site string(100), mode_1_D-T string(200), mode_2_D-T string(200), mode_3_D-T string(200), mode_4_D-T string(200), mode_5_D-T string(200), mode_6_D-T string(200), mode_7_D-T string(200), mode_8_D-T string(200), mode_9_D-T string(200), mode_10_D-T string(200), mode_11_D-T string(200), mode_12_D-T string(200), mode_13_D-T string(200), mode_14_D-T string(200), mode_15_D-T string(200), mode_16_D-T string(200), mode_1_Pro string(200), mode_2_Pro string(200), mode_3_Pro string(200), mode_4_Pro string(200), mode_5_Pro string(200), mode_6_Pro string(200), mode_7_Pro string(200), mode_8_Pro string(200), mode_9_Pro string(200), mode_10_Pro string(200), mode_11_Pro string(200), mode_12_Pro string(200),
      mode_13_Pro string(200), mode_14_Pro string(200), mode_15_Pro string(200), mode_16_Pro string(200), nb_utilisateurs_D-T number(20), nb_depl_pendulaires number(20), nb_depl_pro number(20), nb_utilisateurs_pro number(20)

Bookmark: Ajout attributs: type de lieu origine et destination
AttributeManager_2
    ATTR_TABLE:
      REMOVE rue
      REMOVE no_entree
      REMOVE npa
      REMOVE localite
      RENAME_SET_VALUE type_id
    USER_EXPOSED_ATTRIBUTES = id
    -> AttributeCreator
    -> AttributeCreator_2
AttributeCreator
    ATTR_TABLE = SET_TO type_origine = @Value(type_id)
    -> FeatureMerger_4 [SUPPLIER]
FeatureMerger_4
    ATTR_ACCUM_MODE = Merge Supplier
    ATTR_CONFLICT_RES = Use Requestor
    IGNORE_NULLS = No
    JOIN_KEYS = @Value(lieu_depart_id) @Value(id_lieu) AUTO
    MERGE_TYPE = Attributes Only
    PROCESS_DUPS = NO
    REJECT_NULL_MISSING_KEYS = No
    SUPPLIERS_FIRST = No
    MERGED -> FeatureMerger_5 [REQUESTOR]
AttributeCreator_2
    ATTR_TABLE = SET_TO type_destination = @Value(type_id)
    -> FeatureMerger_5 [SUPPLIER]
FeatureMerger_5
    ATTR_ACCUM_MODE = Merge Supplier
    ATTR_CONFLICT_RES = Use Requestor
    IGNORE_NULLS = No
    JOIN_KEYS = @Value(lieu_arrivee_id) @Value(id_lieu) AUTO
    MERGE_TYPE = Attributes Only
    PROCESS_DUPS = NO
    REJECT_NULL_MISSING_KEYS = No
    SUPPLIERS_FIRST = No
    MERGED -> Tester_Pendulaires

Bookmark: Redéfinition des motifs
Tester_Pendulaires
    BOOL_OP = COMPOSITE
    COMPOSITE_TEST = ( 1 AND 2 ) OR ( 3 AND 4 ) OR ( 5 AND 6 ) OR ( 7 AND 8 )
    TEST_CLAUSE:
      TEST @Value(type_origine) = 1
      TEST @Value(type_destination) = 2
      TEST @Value(type_origine) = 2
      TEST @Value(type_destination) = 1
      TEST @Value(type_origine) = 7
      TEST @Value(type_destination) = 2
      TEST @Value(type_origine) = 2
      TEST @Value(type_destination) = 7
    TEST_MODE = TEST
    PASSED -> Tester_Motif
    FAILED -> Tester_Pendulaires_pro
Tester_Motif
    BOOL_OP = OR
    TEST_CLAUSE:
      TEST @Value(motif_id) = 8
      TEST @Value(motif_id) = 7
      TEST @Value(motif_id) = 11
      TEST @Value(motif_id) = 6
    TEST_MODE = TEST
    PASSED -> AttributeCreator_6
AttributeCreator_6
    ATTR_TABLE = SET_TO motif_defini_id = FME_CONDITIONAL:DEFAULT_VALUE'_FME_NO_OP_'BOOL_OP;OR;COMPOSITE_TEST;1;TEST @Value(nom_motif) = Domicile-travail (direct)'1'BOOL_OP;OR;COMPOSITE_TEST;1;TEST @Value(nom_motif) = Domicile-travail (non direct/avec activité ou contrainte personnelle)'2'BOOL_OP;OR;COMPOSITE_TEST;1;TEST @Value(nom_motif) = Repas de midi'6'BOOL_OP;OR;COMPOSITE_TEST;1;TEST @Value(nom_motif) = Professionnel'3'FME_NUM_CONDITIONS5___
    -> FeatureMerger_Deplacements-utilisateurs [REQUESTOR]
    -> FeatureMerger_Deplacements-profils [REQUESTOR]
Tester_Pendulaires_pro
    BOOL_OP = COMPOSITE
    COMPOSITE_TEST = ( 1 AND ( 2 OR 3 OR 4 )) OR (( 5 OR 6 OR 7 ) AND 8 )
    TEST_CLAUSE:
      TEST @Value(type_origine) = 1
      TEST @Value(type_destination) = 3
      TEST @Value(type_destination) = 4
      TEST @Value(type_destination) = 5
      TEST @Value(type_origine) = 3
      TEST @Value(type_origine) = 4
      TEST @Value(type_origine) = 5
      TEST @Value(type_destination) = 1
    TEST_MODE = TEST
    PASSED -> Tester_Motif_2
    FAILED -> Tester_Repas_pendulaires
Tester_Motif_2
    BOOL_OP = OR
    TEST_CLAUSE:
      TEST @Value(motif_id) = 6
      TEST @Value(motif_id) = 7
      TEST @Value(motif_id) = 8
      TEST @Value(motif_id) = 11
    TEST_MODE = TEST
    PASSED -> AttributeCreator_5
AttributeCreator_5
    ATTR_TABLE = SET_TO motif_defini_id = FME_CONDITIONAL:DEFAULT_VALUE'_FME_NO_OP_'BOOL_OP;OR;COMPOSITE_TEST;1;TEST @Value(nom_motif) = Domicile-travail (direct)'3'BOOL_OP;OR;COMPOSITE_TEST;1;TEST @Value(nom_motif) = Domicile-travail (non direct/avec activité ou contrainte personnelle)'4'BOOL_OP;OR;COMPOSITE_TEST;1;TEST @Value(nom_motif) = Professionnel'3'BOOL_OP;OR;COMPOSITE_TEST;1;TEST @Value(nom_motif) = Repas de midi'6'FME_NUM_CONDITIONS5___
    -> FeatureMerger_Deplacements-utilisateurs [REQUESTOR]
    -> FeatureMerger_Deplacements-profils [REQUESTOR]
Tester_Repas_pendulaires
    BOOL_OP = COMPOSITE
    COMPOSITE_TEST = ( 1 AND 2 ) OR ( 3 AND 4 )
    TEST_CLAUSE:
      TEST @Value(type_origine) = 2
      TEST @Value(type_destination) = 6
      TEST @Value(type_origine) = 6
      TEST @Value(type_destination) = 2
    TEST_MODE = TEST
    PASSED -> Tester_Motif_3
    FAILED -> Tester_Repas_pro
Tester_Motif_3
    BOOL_OP = OR
    TEST_CLAUSE = TEST @Value(motif_id) = 11
    TEST_MODE = TEST
    PASSED -> AttributeCreator_4
AttributeCreator_4
    ATTR_TABLE = SET_TO motif_defini_id = 7
    -> FeatureMerger_Deplacements-utilisateurs [REQUESTOR]
    -> FeatureMerger_Deplacements-profils [REQUESTOR]
Tester_Repas_pro
    BOOL_OP = COMPOSITE
    COMPOSITE_TEST = (( 1 OR 2 OR 3 ) AND 4 ) OR ( 5 AND ( 6 OR 7 OR 8 ))
    TEST_CLAUSE:
      TEST @Value(type_origine) = 3
      TEST @Value(type_origine) = 4
      TEST @Value(type_origine) = 5
      TEST @Value(type_destination) = 6
      TEST @Value(type_origine) = 6
      TEST @Value(type_destination) = 3
      TEST @Value(type_destination) = 4
      TEST @Value(type_destination) = 5
    TEST_MODE = TEST
    PASSED -> Tester_Motif_5
    FAILED -> Tester_Professionnels
Tester_Motif_5
    BOOL_OP = OR
    TEST_CLAUSE:
      TEST @Value(motif_id) = 11
      TEST @Value(motif_id) = 6
    TEST_MODE = TEST
    PASSED -> AttributeCreator_7
AttributeCreator_7
    ATTR_TABLE = SET_TO motif_defini_id = 8
    -> FeatureMerger_Deplacements-utilisateurs [REQUESTOR]
    -> FeatureMerger_Deplacements-profils [REQUESTOR]
Tester_Professionnels
    BOOL_OP = COMPOSITE
    COMPOSITE_TEST = (( 1 OR 2 OR 3 ) AND ( 4 OR 5 OR 6 )) OR (( 7 OR 8 OR 9 ) AND 10 ) OR ( 11 AND ( 12 OR 13 OR 14 )) OR ( 15 AND 16 )
    TEST_CLAUSE:
      TEST @Value(type_origine) = 3
      TEST @Value(type_origine) = 4
      TEST @Value(type_origine) = 5
      TEST @Value(type_destination) = 3
      TEST @Value(type_destination) = 4
      TEST @Value(type_destination) = 5
      TEST @Value(type_origine) = 3
      TEST @Value(type_origine) = 4
      TEST @Value(type_origine) = 5
      TEST @Value(type_destination) = 2
      TEST @Value(type_origine) = 2
      TEST @Value(type_destination) = 3
      TEST @Value(type_destination) = 4
      TEST @Value(type_destination) = 5
      TEST @Value(type_origine) = 2
      TEST @Value(type_destination) = 2
    TEST_MODE = TEST
    PASSED -> Tester_Motif_4
Tester_Motif_4
    BOOL_OP = OR
    TEST_CLAUSE:
      TEST @Value(motif_id) = 6
      TEST @Value(motif_id) = 11
    TEST_MODE = TEST
    PASSED -> AttributeCreator_3
AttributeCreator_3
    ATTR_TABLE = SET_TO motif_defini_id = FME_CONDITIONAL:DEFAULT_VALUE'_FME_NO_OP_'BOOL_OP;OR;COMPOSITE_TEST;1;TEST @Value(nom_motif) = Professionnel'5'BOOL_OP;OR;COMPOSITE_TEST;1;TEST @Value(nom_motif) = Repas de midi'8'FME_NUM_CONDITIONS3___
    -> FeatureMerger_Deplacements-utilisateurs [REQUESTOR]
    -> FeatureMerger_Deplacements-profils [REQUESTOR]

Bookmark: Traitement des utilisateurs.trices
auth_user (reader POSTGRES_1)
    attributes: id serial,PrimaryKey, password varchar(128), last_login timestamptz, is_superuser bool, username varchar(150),Unique, first_name varchar(150), last_name varchar(150), email varchar(254), is_staff bool, is_active bool, date_joined timestamptz
    -> AttributeKeeper_2
AttributeKeeper_2
    CREATE_BULK_MODE_FEATURES = NO
    KEEP_ATTRS = id,username
    -> Tester
Tester
    BOOL_OP = COMPOSITE
    COMPOSITE_TEST = 1 AND 2 AND 3 AND 4
    TEST_CLAUSE:
      TEST @Value(username) NOT_= mathieua
      TEST @Value(username) NOT_= delacretaz
      TEST @Value(username) NOT_= ingensand
      TEST @Value(username) NOT_= manoni
    TEST_MODE = TEST
    PASSED -> FeatureMerger_16 [REQUESTOR]

Bookmark: Statistiques utilisateurs.trices selon déplacements D-T et pro
StatisticsCalculator_nb_mode_par_utilisateur_D-T
    CALCULATION_MODE = NUMERIC
    FEAT_STATS = mode_id,NUMERIC_MODE,,,COUNT,,,,,,,,,,
    GROUP_BY = mode_id utilisateur_id
    SUMMARY -> StatisticsCalculator_nb_mode_par_utilisateur_D-T_2
StatisticsCalculator_nb_mode_par_utilisateur_D-T_2
    CALCULATION_MODE = NUMERIC
    FEAT_STATS = utilisateur_id,NUMERIC_MODE,,,COUNT,,,,,,,,,,
    GROUP_BY = utilisateur_id
    SUMMARY -> AttributeRenamer_9
AttributeRenamer_9
    ATTR_TABLE = RENAME_SET_DEFAULT utilisateur_id.total_count > nb_modes_differents
    MISSING_INPUT_ATTRS = REMOVE
    -> FeatureMerger_66 [REQUESTOR]
StatisticsCalculator_nb_depl_par_utilisateur_D-T
    CALCULATION_MODE = NUMERIC
    FEAT_STATS = id_deplacement,NUMERIC_MODE,,,COUNT,,,,,,,,,,
    GROUP_BY = utilisateur_id
    SUMMARY -> AttributeRenamer_15
AttributeRenamer_15
    ATTR_TABLE = RENAME_SET_DEFAULT id_deplacement.total_count > nb_depl
    MISSING_INPUT_ATTRS = REMOVE
    -> FeatureMerger_66 [SUPPLIER]
FeatureMerger_66
    ATTR_ACCUM_MODE = Merge Supplier
    ATTR_CONFLICT_RES = Use Requestor
    IGNORE_NULLS = No
    JOIN_KEYS = @Value(utilisateur_id) @Value(utilisateur_id) AUTO
    MERGE_TYPE = Attributes Only
    PROCESS_DUPS = NO
    REJECT_NULL_MISSING_KEYS = No
    SUPPLIERS_FIRST = No
    MERGED -> Statistiques_utilisateurs_D-T (writer XLSXW_2)
    MERGED -> Statistiques_utilisateurs_D-T (writer XLSXW_4)
Statistiques_utilisateurs_D-T (writer XLSXW_2)
    attributes: utilisateur_id number(20), nb_modes_differents number(20), nb_depl number(20)
Statistiques_utilisateurs_D-T (writer XLSXW_4)
    attributes: utilisateur_id number(20), nb_modes_differents number(20), nb_depl number(20)
StatisticsCalculator_nb_mode_par_utilisateur_pro
    CALCULATION_MODE = NUMERIC
    FEAT_STATS = mode_id,NUMERIC_MODE,,,COUNT,,,,,,,,,,
    GROUP_BY = mode_id utilisateur_id
    SUMMARY -> StatisticsCalculator_nb_mode_par_utilisateur_pro_2
StatisticsCalculator_nb_mode_par_utilisateur_pro_2
    CALCULATION_MODE = NUMERIC
    FEAT_STATS = utilisateur_id,NUMERIC_MODE,,,COUNT,,,,,,,,,,
    GROUP_BY = utilisateur_id
    SUMMARY -> AttributeRenamer_10
AttributeRenamer_10
    ATTR_TABLE = RENAME_SET_DEFAULT utilisateur_id.total_count > nb_modes_differents
    MISSING_INPUT_ATTRS = REMOVE
    -> FeatureMerger_67 [REQUESTOR]
StatisticsCalculator_nb_depl_par_utilisateur_pro
    CALCULATION_MODE = NUMERIC
    FEAT_STATS = id_deplacement,NUMERIC_MODE,,,COUNT,,,,,,,,,,
    GROUP_BY = utilisateur_id
    SUMMARY -> AttributeRenamer_16
AttributeRenamer_16
    ATTR_TABLE = RENAME_SET_DEFAULT id_deplacement.total_count > nb_depl
    MISSING_INPUT_ATTRS = REMOVE
    -> FeatureMerger_67 [SUPPLIER]
FeatureMerger_67
    ATTR_ACCUM_MODE = Merge Supplier
    ATTR_CONFLICT_RES = Use Requestor
    IGNORE_NULLS = No
    JOIN_KEYS = @Value(utilisateur_id) @Value(utilisateur_id) AUTO
    MERGE_TYPE = Attributes Only
    PROCESS_DUPS = NO
    REJECT_NULL_MISSING_KEYS = No
    SUPPLIERS_FIRST = No
    MERGED -> Statistiques_utilisateurs_pro (writer XLSXW_2)
    MERGED -> Statistiques_utilisateurs_pro (writer XLSXW_4)
Statistiques_utilisateurs_pro (writer XLSXW_2)
    attributes: utilisateur_id number(20), nb_modes_differents number(20), nb_depl number(20)
Statistiques_utilisateurs_pro (writer XLSXW_4)
    attributes: utilisateur_id number(20), nb_modes_differents number(20), nb_depl number(20)

Bookmark: Statistiques par motif défini, nombre de déplacements
StatisticsCalculator_Motif_defini
    CALCULATION_MODE = NUMERIC
    FEAT_STATS = id_deplacement,NUMERIC_MODE,,,COUNT,,,,,,,,,,
    GROUP_BY = motif_defini_id
    SUMMARY -> Sorter_12
Sorter_12
    SORT_PARM = motif_defini_id NATURAL ASCENDING
    SORTED -> Statistiques_Motif_defini (writer XLSXW_2)
Statistiques_Motif_defini (writer XLSXW_2)
    attributes: motif_defini_id string(200), id_deplacement.total_count number(20)

Bookmark: Statistiques de l'influence de Bike to work
Tester_Velo_Velo-TP_Semaine_1
    BOOL_OP = COMPOSITE
    COMPOSITE_TEST = 1 OR 2 AND ( 3 OR 4 OR 5 OR 6 OR 7 )
    TEST_CLAUSE:
      TEST @Value(nom_mode) = Vélo, vélo électrique
      TEST @Value(nom_mode) = Vélo et transports publics
      TEST @Value(date) = 20230424
      TEST @Value(date) = 20230425
      TEST @Value(date) = 20230426
      TEST @Value(date) = 20230427
      TEST @Value(date) = 20230428
    TEST_MODE = TEST
    PASSED -> StatisticsCalculator_2
StatisticsCalculator_2
    CALCULATION_MODE = NUMERIC
    FEAT_STATS = id_deplacement,NUMERIC_MODE,,,COUNT,,,,,,,,,,
    SUMMARY -> AttributeManager_17
AttributeManager_17
    ATTR_TABLE = RENAME_SET_VALUE id_deplacement.total_count > nb_depl_velo_semaine_1
    -> Statistiques_Bike_to_Work (writer XLSXW_2)
Tester_Velo_Velo-TP_Semaine_2
    BOOL_OP = COMPOSITE
    COMPOSITE_TEST = 1 OR 2 AND ( 3 OR 4 OR 5 OR 6 OR 7 )
    TEST_CLAUSE:
      TEST @Value(nom_mode) = Vélo, vélo électrique
      TEST @Value(nom_mode) = Vélo et transports publics
      TEST @Value(date) = 20230501
      TEST @Value(date) = 20230502
      TEST @Value(date) = 20230503
      TEST @Value(date) = 20230504
      TEST @Value(date) = 20230505
    TEST_MODE = TEST
    PASSED -> StatisticsCalculator_6
StatisticsCalculator_6
    CALCULATION_MODE = NUMERIC
    FEAT_STATS = id_deplacement,NUMERIC_MODE,,,COUNT,,,,,,,,,,
    SUMMARY -> AttributeManager_20
AttributeManager_20
    ATTR_TABLE = RENAME_SET_VALUE id_deplacement.total_count > nb_depl_velo_semaine_2
    -> Statistiques_Bike_to_Work (writer XLSXW_2)
Statistiques_Bike_to_Work (writer XLSXW_2)
    attributes: nb_depl_velo_semaine_1 number(20), nb_depl_velo_semaine_2 number(20)

Bookmark: Statistiques des profils utilisateurs.trices
StatisticsCalculator_7
    CALCULATION_MODE = NUMERIC
    FEAT_STATS = id,NUMERIC_MODE,,,COUNT,,,,,,,,,,
    SUMMARY -> AttributeManager_24
AttributeManager_24
    ATTR_TABLE:
      RENAME_SET_VALUE id.total_count > nb_personnes_depl+profil
      SET_TO nb_personnes_depl = FME_NULL_VALUE
      SET_TO nb_personnes_profil = FME_NULL_VALUE
    -> Nb_utilisateurs (writer XLSXW_1)
StatisticsCalculator_8
    CALCULATION_MODE = NUMERIC
    FEAT_STATS = id,NUMERIC_MODE,,,COUNT,,,,,,,,,,
    SUMMARY -> AttributeManager_26
AttributeManager_26
    ATTR_TABLE:
      SET_TO nb_personnes_depl+profil = FME_NULL_VALUE
      SET_TO nb_personnes_depl = FME_NULL_VALUE
      RENAME_SET_VALUE id.total_count > nb_personnes_profil
    -> Nb_utilisateurs (writer XLSXW_1)
StatisticsCalculator_9
    CALCULATION_MODE = NUMERIC
    FEAT_STATS = utilisateur_id,NUMERIC_MODE,,,COUNT,,,,,,,,,,
    SUMMARY -> AttributeManager_27
AttributeManager_27
    ATTR_TABLE:
      SET_TO nb_personnes_depl+profil = FME_NULL_VALUE
      RENAME_SET_VALUE utilisateur_id.total_count > nb_personnes_depl
      SET_TO nb_personnes_profil = FME_NULL_VALUE
    USER_EXPOSED_ATTRIBUTES = id.total_count
    -> Nb_utilisateurs (writer XLSXW_1)
Nb_utilisateurs (writer XLSXW_1)
    attributes: nb_personnes_depl+profil number(20), nb_personnes_depl number(20), nb_personnes_profil number(20)
StatisticsCalculator_Profil_par_societe
    CALCULATION_MODE = NUMERIC
    FEAT_STATS = id,NUMERIC_MODE,,,COUNT,,,,,,,,,,
    GROUP_BY = societe_id
    SUMMARY -> FeatureMerger_30 [SUPPLIER]
FeatureMerger_30
    ATTR_ACCUM_MODE = Merge Supplier
    ATTR_CONFLICT_RES = Use Requestor
    IGNORE_NULLS = No
    JOIN_KEYS = @Value(id_societe) @Value(societe_id) AUTO
    MERGE_TYPE = Attributes Only
    PROCESS_DUPS = NO
    REJECT_NULL_MISSING_KEYS = No
    SUPPLIERS_FIRST = No
    MERGED -> Sorter_11
    UNMERGED_REQUESTOR -> Sorter_11
Sorter_11
    SORT_PARM = id_societe NATURAL ASCENDING
    SORTED -> Societes (writer XLSXW_1)
Societes (writer XLSXW_1)
    attributes: id_societe number(20), nom_societe string(100), id.total_count number(20)
StatisticsCalculator_Profil_par_site
    CALCULATION_MODE = NUMERIC
    FEAT_STATS = id,NUMERIC_MODE,,,COUNT,,,,,,,,,,
    GROUP_BY = site_id
    SUMMARY -> FeatureMerger_31 [SUPPLIER]
FeatureMerger_31
    ATTR_ACCUM_MODE = Merge Supplier
    ATTR_CONFLICT_RES = Use Requestor
    IGNORE_NULLS = No
    JOIN_KEYS = @Value(id_site) @Value(site_id) AUTO
    MERGE_TYPE = Attributes Only
    PROCESS_DUPS = NO
    REJECT_NULL_MISSING_KEYS = No
    SUPPLIERS_FIRST = No
    MERGED -> Sorter_10
    UNMERGED_REQUESTOR -> Sorter_10
Sorter_10
    SORT_PARM = id_site NATURAL ASCENDING
    SORTED -> Sites (writer XLSXW_1)
Sites (writer XLSXW_1)
    attributes: id_site number(20), nom_site string(100), id.total_count number(20)
StatisticsCalculator_Profil_par_fonction
    CALCULATION_MODE = NUMERIC
    FEAT_STATS = id,NUMERIC_MODE,,,COUNT,,,,,,,,,,
    GROUP_BY = fonction_id
    SUMMARY -> FeatureMerger_32 [SUPPLIER]
FeatureMerger_32
    ATTR_ACCUM_MODE = Merge Supplier
    ATTR_CONFLICT_RES = Use Requestor
    IGNORE_NULLS = No
    JOIN_KEYS = @Value(id_fonction) @Value(fonction_id) AUTO
    MERGE_TYPE = Attributes Only
    PROCESS_DUPS = NO
    REJECT_NULL_MISSING_KEYS = No
    SUPPLIERS_FIRST = No
    MERGED -> Sorter_9
    UNMERGED_REQUESTOR -> Sorter_9
Sorter_9
    SORT_PARM = id_fonction NATURAL ASCENDING
    SORTED -> Fonction (writer XLSXW_1)
Fonction (writer XLSXW_1)
    attributes: id_fonction number(20), nom_fonction string(100), id.total_count number(20)
StatisticsCalculator_Profil_par_taux
    CALCULATION_MODE = NUMERIC
    FEAT_STATS = id,NUMERIC_MODE,,,COUNT,,,,,,,,,,
    GROUP_BY = taux_id
    SUMMARY -> FeatureMerger_33 [SUPPLIER]
FeatureMerger_33
    ATTR_ACCUM_MODE = Merge Supplier
    ATTR_CONFLICT_RES = Use Requestor
    IGNORE_NULLS = No
    JOIN_KEYS = @Value(id_taux) @Value(taux_id) AUTO
    MERGE_TYPE = Attributes Only
    PROCESS_DUPS = NO
    REJECT_NULL_MISSING_KEYS = No
    SUPPLIERS_FIRST = No
    MERGED -> Sorter_8
    UNMERGED_REQUESTOR -> Sorter_8
Sorter_8
    SORT_PARM = id_taux NATURAL ASCENDING
    SORTED -> Taux (writer XLSXW_1)
Taux (writer XLSXW_1)
    attributes: taux string(3), id.total_count number(20)
StatisticsCalculator_Profil_par_teletravail
    CALCULATION_MODE = NUMERIC
    FEAT_STATS = id,NUMERIC_MODE,,,COUNT,,,,,,,,,,
    GROUP_BY = teletravail_id
    SUMMARY -> FeatureMerger_34 [SUPPLIER]
FeatureMerger_34
    ATTR_ACCUM_MODE = Merge Supplier
    ATTR_CONFLICT_RES = Use Requestor
    IGNORE_NULLS = No
    JOIN_KEYS = @Value(id_teletravail) @Value(teletravail_id) AUTO
    MERGE_TYPE = Attributes Only
    PROCESS_DUPS = NO
    REJECT_NULL_MISSING_KEYS = No
    SUPPLIERS_FIRST = No
    MERGED -> Sorter_7
    UNMERGED_REQUESTOR -> Sorter_7
Sorter_7
    SORT_PARM = id_teletravail NATURAL ASCENDING
    SORTED -> Teletravail (writer XLSXW_1)
Teletravail (writer XLSXW_1)
    attributes: teletravail string(3), id.total_count number(20)
StatisticsCalculator_Profil_par_PMR
    CALCULATION_MODE = NUMERIC
    FEAT_STATS = id,NUMERIC_MODE,,,COUNT,,,,,,,,,,
    GROUP_BY = pmr
    SUMMARY -> PMR (writer XLSXW_1)
PMR (writer XLSXW_1)
    attributes: pmr boolean(20), id.total_count number(20)
StatisticsCalculator_Profil_par_Bike_to_work
    CALCULATION_MODE = NUMERIC
    FEAT_STATS = id,NUMERIC_MODE,,,COUNT,,,,,,,,,,
    GROUP_BY = bike_to_work
    SUMMARY -> Bike_to_work (writer XLSXW_1)
Bike_to_work (writer XLSXW_1)
    attributes: bike_to_work boolean(20), id.total_count number(20)
