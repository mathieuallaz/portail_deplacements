FME workspace 4_calcul_API_Transport.fmw

Parameters:
- SourceDataset_XLSXR = $(FME_MF_DIR)coord_deplacements_TP.xlsx   # Source Microsoft Excel File(s)
- DestDataset_XLSXW = $(FME_MF_DIR)temps_parcours_TP.xlsx   # Destination Microsoft Excel File

Readers:
- XLSXR_1: XLSXR from $(SourceDataset_XLSXR)

Writers:
- XLSXW_1: XLSXW to $(DestDataset_XLSXW)

coord_deplacements_TP (reader XLSXR_1)
    attributes: id_deplacement number(5,0), date date, heure_depart time, nom_mode char(44), x_destination number(16,14), y_destination number(16,13), x_origine x_coordinate, y_origine y_coordinate
    -> AttributeManager_7
AttributeManager_7
    ATTR_TABLE:
      SET_TO coord_trajet = @Value(x_origine),@Value(y_origine);@Value(x_destination),@Value(y_destination)
      SET_TO coord_origine = @Value(x_origine),@Value(y_origine)
      SET_TO coord_destination = @Value(x_destination),@Value(y_destination)
    USER_EXPOSED_ATTRIBUTES = id_deplacement.total_count
    -> Counter
Counter
    CNT_ATTR = _count
    DOMAIN = counter
    SCOPE = Global
    START = 1
    -> Tester
Tester
    BOOL_OP = OR
    TEST_CLAUSE = TEST @Value(_count) > 1134
    TEST_MODE = TEST
    PASSED -> Decelerator
Decelerator
    DECEL_TYPE = Limit Features Per Second
    FEATURES_PER_SECOND = 1
    -> HTTPCaller_API_Transport
FeatureMerger
    ATTR_ACCUM_MODE = Merge Supplier
    ATTR_CONFLICT_RES = Use Requestor
    IGNORE_NULLS = No
    JOIN_KEYS = @Value(id_deplacement) @Value(id_deplacement) AUTO
    MERGE_TYPE = Attributes Only
    PROCESS_DUPS = NO
    REJECT_NULL_MISSING_KEYS = No
    SUPPLIERS_FIRST = No
    MERGED -> AttributeKeeper
AttributeKeeper
    CREATE_BULK_MODE_FEATURES = NO
    KEEP_ATTRS = id_deplacement,nb_transfert,temps_TP_min
    -> temps_parcours_TP (writer XLSXW_1)
temps_parcours_TP (writer XLSXW_1)
    attributes: id_deplacement number(5), temps_TP_min string(200), nb_transfert string(200)

Bookmark: Calcul temps parcours par TP avec API Transport de opendata
HTTPCaller_API_Transport
    ADDITIONAL_URL_PARAMETERS = from;@Value(coord_origine) to;@Value(coord_destination) date;@Value(date) time;@Value(heure_depart)
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = http://transport.opendata.ch/v1/connections?
    TRANSFER_TIMEOUT_LENGTH = 90
    USE_COOKIES = No
    VERIFY_SSL_CERTIFICATES = Yes
    -> StringSearcher_2
    -> StringSearcher_3
StringSearcher_2
    CASE = no
    MATCHED_RESULT_ATTR = _first_match
    REGEXP = "duration":"([0-9]*)d([0-9]*):([0-9]*):([0-9]*)"
    STRING_TO_SEARCH = @Value(_response_body)
    MATCHED -> AttributeSplitter_4
AttributeSplitter_4
    ATTR_NAME = _first_match
    DELIMITER = "
    DROP_EMPTY_PARTS = No
    LIST_NAME = _list
    TRIM_OPTION = Both
    -> AttributeSplitter_5
AttributeSplitter_5
    ATTR_NAME = _list{3}
    DELIMITER = d
    DROP_EMPTY_PARTS = No
    LIST_NAME = _jours
    TRIM_OPTION = Both
    -> AttributeSplitter_6
AttributeSplitter_6
    ATTR_NAME = _jours{1}
    DELIMITER = :
    DROP_EMPTY_PARTS = No
    LIST_NAME = _heures
    TRIM_OPTION = Both
    -> AttributeManager
AttributeManager
    ATTR_TABLE = SET_TO temps_TP_min = @Evaluate(@Value(_jours{0})*1440+@Value(_heures{0})*60+@Value(_heures{1}))
    USER_EXPOSED_ATTRIBUTES = id_deplacement.total_count
    -> FeatureMerger [REQUESTOR]
StringSearcher_3
    CASE = no
    MATCHED_RESULT_ATTR = _first_match
    REGEXP = "transfers":([0-9]*)
    STRING_TO_SEARCH = @Value(_response_body)
    MATCHED -> AttributeSplitter_2
AttributeSplitter_2
    ATTR_NAME = _first_match
    DELIMITER = :
    DROP_EMPTY_PARTS = No
    LIST_NAME = _list
    TRIM_OPTION = Both
    -> AttributeManager_2
AttributeManager_2
    ATTR_TABLE:
      REMOVE _count
      REMOVE _response_body
      REMOVE _http_status_code
      REMOVE _first_match
      SET_TO nb_transfert = @Value(_list{1})
    -> FeatureMerger [SUPPLIER]
