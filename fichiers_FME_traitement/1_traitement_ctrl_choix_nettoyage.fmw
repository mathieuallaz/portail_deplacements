FME workspace 1_traitement_ctrl_choix_nettoyage.fmw

Parameters:
- SourceDataset_POSTGIS = portail_gdb   # Connection
- SourceDataset_POSTGRES = portail_gdb   # Connection

Readers:
- POSTGIS_1: POSTGIS from $(SourceDataset_POSTGIS)
- POSTGRES_1: POSTGRES from $(SourceDataset_POSTGRES)

FeatureMerger_utilisateurs.trices-profil
    ATTR_ACCUM_MODE = Merge Supplier
    ATTR_CONFLICT_RES = Use Requestor
    IGNORE_NULLS = No
    JOIN_KEYS = @Value(id) @Value(utilisateur_id) AUTO
    MERGE_TYPE = Attributes Only
    PROCESS_DUPS = NO
    REJECT_NULL_MISSING_KEYS = No
    SUPPLIERS_FIRST = No
    MERGED -> Junction_5
    MERGED -> Junction_21
    MERGED -> Junction_27
    MERGED -> Junction_31
    MERGED -> Junction_33
    MERGED -> Junction_43
    MERGED -> Junction_47
    MERGED -> Junction_51
    UNMERGED_REQUESTOR -> Junction_7
    UNMERGED_REQUESTOR -> Junction_23
    UNMERGED_REQUESTOR -> Junction_25
    UNMERGED_REQUESTOR -> Junction_35
    UNMERGED_REQUESTOR -> Junction_37
    UNMERGED_REQUESTOR -> Junction_41
    UNMERGED_REQUESTOR -> Junction_45
    UNMERGED_REQUESTOR -> Junction_49
Note: après nettoyage et contrôle
Note: FeatureMerger_15 : Supplier
Junction_5
    -> Junction_6
Note: FeatureMerger_15 : Supplier
Junction_7
    -> Junction_8
Note: FeatureMerger_16 : Supplier
Junction_25
    -> Junction_26
Note: FeatureMerger_16 : Supplier
Junction_27
    -> Junction_28
Note: FeatureMerger_24 : Supplier
Junction_35
    -> Junction_36
Note: FeatureMerger_24 : Supplier
Junction_31
    -> Junction_32
Note: FeatureMerger_utilisateurs.trices_avec_autres_paires : Supplier
Junction_47
    -> Junction_48
Note: FeatureMerger_utilisateurs.trices_avec_autres_paires : Supplier
Junction_45
    -> Junction_46
Note: FeatureMerger_deplacements-utilisateurs.trices : Supplier
Junction_33
    -> Junction_34
Note: Tri par utilisateur.trice, date, heure départ. Calcul des statistiques pour connaître le nombre de déplacements par jour et par utilisateur. Test afin d’extraire les jours avec qu’un seul déplacement (non conservés). Agrégation des lieux de départ et d’arrivée. Création de liste par AttributeSplitter. Test en boucle pour contrôle que lieu de départ = lieu d’arrivée du précédent trajet. Mise en évidence des trajets dont le sens n’a pas été modifié.
Note: FeatureMerger_utilisateurs.trices-profil : Merged
Junction_34
    -> FeatureMerger_deplacements-utilisateurs.trices [SUPPLIER]
Note: FeatureMerger_deplacements-utilisateurs.trices : Supplier
Junction_37
    -> Junction_38
Note: FeatureMerger_utilisateurs.trices-profil : UnmergedRequestor
Junction_38
    -> FeatureMerger_deplacements-utilisateurs.trices [SUPPLIER]
FeatureMerger_deplacements-utilisateurs.trices
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    MERGED -> StatisticsCalculator_nb_deplacement
    UNMERGED_REQUESTOR -> StatisticsCalculator_nb_deplacement
Note: FeatureMerger_35 : Supplier
Junction_51
    -> Junction_52
Note: FeatureMerger_35 : Supplier
Junction_41
    -> Junction_42
Note: FeatureMerger_36 : Supplier
Junction_49
    -> Junction_50
Note: FeatureMerger_36 : Supplier
Junction_43
    -> Junction_44
Note: FeatureMerger_37 : Supplier
Junction_23
    -> Junction_24
Note: FeatureMerger_37 : Supplier
Junction_21
    -> Junction_22

Bookmark: Gestion des clés étrangères des profils
deplacements_fonction (reader POSTGRES_1)
    attributes: id_fonction serial,PrimaryKey, nom_fonction varchar(100), alias_fonction varchar(100)
    -> FeatureMerger_12 [SUPPLIER]
deplacements_teletravail (reader POSTGRES_1)
    attributes: id_teletravail serial,PrimaryKey, teletravail varchar(3)
    -> FeatureMerger_14 [SUPPLIER]
deplacements_societe_sites (reader POSTGRES_1)
    attributes: id int8,PrimaryKey, societe_id int4,BTREE, site_id int4,BTREE
deplacements_profil (reader POSTGRES_1)
    attributes: id_profil serial,PrimaryKey, pmr bool, bike_to_work bool, fonction_id int4,BTREE, site_id int4,BTREE, societe_id int4,BTREE, taux_id int4,BTREE, utilisateur_id int4,Unique, teletravail_id int4,BTREE
    -> FeatureMerger_10 [REQUESTOR]
deplacements_societe (reader POSTGRES_1)
    attributes: id_societe serial,PrimaryKey, nom_societe varchar(100)
    -> FeatureMerger_10 [SUPPLIER]
FeatureMerger_10
    ATTR_ACCUM_MODE = Merge Supplier
    ATTR_CONFLICT_RES = Use Requestor
    IGNORE_NULLS = No
    JOIN_KEYS = @Value(societe_id) @Value(id_societe) AUTO
    MERGE_TYPE = Attributes Only
    PROCESS_DUPS = NO
    REJECT_NULL_MISSING_KEYS = No
    SUPPLIERS_FIRST = No
    MERGED -> FeatureMerger_11 [REQUESTOR]
deplacements_site (reader POSTGRES_1)
    attributes: id_site serial,PrimaryKey, nom_site varchar(100), lieu_id int4,BTREE
    -> FeatureMerger_11 [SUPPLIER]
FeatureMerger_11
    ATTR_ACCUM_MODE = Merge Supplier
    ATTR_CONFLICT_RES = Use Requestor
    IGNORE_NULLS = No
    JOIN_KEYS = @Value(site_id) @Value(id_site) AUTO
    MERGE_TYPE = Attributes Only
    PROCESS_DUPS = NO
    REJECT_NULL_MISSING_KEYS = No
    SUPPLIERS_FIRST = No
    MERGED -> FeatureMerger_12 [REQUESTOR]
FeatureMerger_12
    ATTR_ACCUM_MODE = Merge Supplier
    ATTR_CONFLICT_RES = Use Requestor
    IGNORE_NULLS = No
    JOIN_KEYS = @Value(fonction_id) @Value(id_fonction) AUTO
    MERGE_TYPE = Attributes Only
    PROCESS_DUPS = NO
    REJECT_NULL_MISSING_KEYS = No
    SUPPLIERS_FIRST = No
    MERGED -> FeatureMerger_13 [REQUESTOR]
deplacements_taux (reader POSTGRES_1)
    attributes: id_taux serial,PrimaryKey, taux varchar(3)
    -> FeatureMerger_13 [SUPPLIER]
FeatureMerger_13
    ATTR_ACCUM_MODE = Merge Supplier
    ATTR_CONFLICT_RES = Use Requestor
    IGNORE_NULLS = No
    JOIN_KEYS = @Value(taux_id) @Value(id_taux) AUTO
    MERGE_TYPE = Attributes Only
    PROCESS_DUPS = NO
    REJECT_NULL_MISSING_KEYS = No
    SUPPLIERS_FIRST = No
    MERGED -> FeatureMerger_14 [REQUESTOR]
FeatureMerger_14
    ATTR_ACCUM_MODE = Merge Supplier
    ATTR_CONFLICT_RES = Use Requestor
    IGNORE_NULLS = No
    JOIN_KEYS = @Value(teletravail_id) @Value(id_teletravail) AUTO
    MERGE_TYPE = Attributes Only
    PROCESS_DUPS = NO
    REJECT_NULL_MISSING_KEYS = No
    SUPPLIERS_FIRST = No
    MERGED -> AttributeManager_15
AttributeManager_15
    ATTR_TABLE:
      REMOVE id_profil
      REMOVE id_societe
      REMOVE id_site
      REMOVE id_fonction
      REMOVE id_taux
      REMOVE id_teletravail
    -> FeatureMerger_utilisateurs.trices-profil [SUPPLIER]

Bookmark: Gestion des clés étrangères des déplacements
deplacements_deplacement (reader POSTGRES_1)
    attributes: id_deplacement serial,PrimaryKey, date date, heure_depart time, heure_arrivee time, lieu_arrivee_id int4,BTREE, lieu_depart_id int4,BTREE, mode_id int4,BTREE, motif_id int4,BTREE, raison_id int4,BTREE, utilisateur_id int4,BTREE
    -> FeatureMerger_6 [REQUESTOR]
deplacements_mode (reader POSTGRES_1)
    attributes: id_mode serial,PrimaryKey, nom_mode varchar(100), alias_mode varchar(100)
    -> FeatureMerger_6 [SUPPLIER]
FeatureMerger_6
    ATTR_ACCUM_MODE = Merge Supplier
    ATTR_CONFLICT_RES = Use Requestor
    IGNORE_NULLS = No
    JOIN_KEYS = @Value(mode_id) @Value(id_mode) AUTO
    MERGE_TYPE = Attributes Only
    PROCESS_DUPS = NO
    REJECT_NULL_MISSING_KEYS = No
    SUPPLIERS_FIRST = No
    MERGED -> FeatureMerger_7 [REQUESTOR]
deplacements_motif (reader POSTGRES_1)
    attributes: id_motif serial,PrimaryKey, nom_motif varchar(150), alias_motif varchar(100)
    -> FeatureMerger_7 [SUPPLIER]
FeatureMerger_7
    ATTR_ACCUM_MODE = Merge Supplier
    ATTR_CONFLICT_RES = Use Requestor
    IGNORE_NULLS = No
    JOIN_KEYS = @Value(motif_id) @Value(id_motif) AUTO
    MERGE_TYPE = Attributes Only
    PROCESS_DUPS = NO
    REJECT_NULL_MISSING_KEYS = No
    SUPPLIERS_FIRST = No
    MERGED -> FeatureMerger_8 [REQUESTOR]
deplacements_raison (reader POSTGRES_1)
    attributes: id_raison serial,PrimaryKey, nom_raison varchar(100), alias_raison varchar(100)
    -> FeatureMerger_8 [SUPPLIER]
FeatureMerger_8
    ATTR_ACCUM_MODE = Merge Supplier
    ATTR_CONFLICT_RES = Use Requestor
    IGNORE_NULLS = No
    JOIN_KEYS = @Value(raison_id) @Value(id_raison) AUTO
    MERGE_TYPE = Attributes Only
    PROCESS_DUPS = NO
    REJECT_NULL_MISSING_KEYS = No
    SUPPLIERS_FIRST = No
    MERGED -> AttributeManager_14
AttributeManager_14
    ATTR_TABLE:
      REMOVE id_mode
      REMOVE id_motif
      REMOVE id_raison
    -> Tester_5

Bookmark: 1. Traitement des déplacements en dehors de l'enquête
Tester_5
    BOOL_OP = AND
    TEST_CLAUSE:
      TEST @Value(date) >= 20230424
      TEST @Value(date) <= 20230505
    TEST_MODE = TEST
    PASSED -> Tester_4

Bookmark: 2. Traitement des déplacements durant le week-end
Tester_4
    BOOL_OP = OR
    TEST_CLAUSE:
      TEST @Value(date) = 20230429
      TEST @Value(date) = 20230430
    TEST_MODE = TEST
    PASSED -> Tester_6
    FAILED -> Tester_6

Bookmark: 3. Traitement des déplacements avec "Chantier test" comme lieu (origine ou destination)
Tester_6
    BOOL_OP = OR
    TEST_CLAUSE:
      TEST @Value(lieu_depart_id) = 19
      TEST @Value(lieu_arrivee_id) = 19
    TEST_MODE = TEST
    FAILED -> Tester_7

Bookmark: 4. Traitement des déplacements des utilisateurs.trices qui ne sont pas employés.es par sdplus
Tester_7
    BOOL_OP = OR
    TEST_CLAUSE:
      TEST @Value(utilisateur_id) = 1
      TEST @Value(utilisateur_id) = 14
      TEST @Value(utilisateur_id) = 15
      TEST @Value(utilisateur_id) = 223
    TEST_MODE = TEST
    FAILED -> Tester_22

Bookmark: 5. Traitement des déplacements dont l'origine et la destination sont identiques
Tester_22
    BOOL_OP = OR
    TEST_CLAUSE = TEST @Value(lieu_depart_id) != @Value(lieu_arrivee_id)
    TEST_MODE = TEST
    PASSED -> FeatureMerger_4 [REQUESTOR]

Bookmark: Gestion des clés étrangères des lieux
deplacements_lieu (reader POSTGIS_1)
    attributes: id serial,PrimaryKey, nom varchar(100), rue varchar(100), no_entree varchar(10), npa int4, localite varchar(50), utilisateur_id int4,BTREE, type_id int4,BTREE
    -> AttributeManager_3
AttributeManager_3
    ATTR_TABLE = RENAME_SET_VALUE id > id_lieu
    -> FeatureMerger_9 [REQUESTOR]
deplacements_type (reader POSTGRES_1)
    attributes: id_type serial,PrimaryKey, nom_type varchar(100), alias_type varchar(100)
    -> FeatureMerger_9 [SUPPLIER]
FeatureMerger_9
    ATTR_ACCUM_MODE = Merge Supplier
    ATTR_CONFLICT_RES = Use Requestor
    IGNORE_NULLS = No
    JOIN_KEYS = @Value(type_id) @Value(id_type) AUTO
    MERGE_TYPE = Attributes and Geometry
    PROCESS_DUPS = NO
    REJECT_NULL_MISSING_KEYS = No
    SUPPLIERS_FIRST = No
    MERGED -> FeatureMerger_4 [REQUESTOR]
    MERGED -> AttributeManager_5

Bookmark: Ajout attributs: type de lieu origine et destination
AttributeManager_5
    ATTR_TABLE:
      REMOVE rue
      REMOVE no_entree
      REMOVE npa
      REMOVE localite
      RENAME_SET_VALUE type_id
    USER_EXPOSED_ATTRIBUTES = id
    -> AttributeCreator
    -> AttributeCreator_2
AttributeCreator
    ATTR_TABLE = SET_TO type_origine = @Value(type_id)
    -> FeatureMerger_4 [SUPPLIER]
FeatureMerger_4
    ATTR_ACCUM_MODE = Merge Supplier
    ATTR_CONFLICT_RES = Use Requestor
    IGNORE_NULLS = No
    JOIN_KEYS = @Value(lieu_depart_id) @Value(id_lieu) AUTO
    MERGE_TYPE = Attributes Only
    PROCESS_DUPS = NO
    REJECT_NULL_MISSING_KEYS = No
    SUPPLIERS_FIRST = No
    MERGED -> FeatureMerger_5 [REQUESTOR]
AttributeCreator_2
    ATTR_TABLE = SET_TO type_destination = @Value(type_id)
    -> FeatureMerger_5 [SUPPLIER]
FeatureMerger_5
    ATTR_ACCUM_MODE = Merge Supplier
    ATTR_CONFLICT_RES = Use Requestor
    IGNORE_NULLS = No
    JOIN_KEYS = @Value(lieu_arrivee_id) @Value(id_lieu) AUTO
    MERGE_TYPE = Attributes Only
    PROCESS_DUPS = NO
    REJECT_NULL_MISSING_KEYS = No
    SUPPLIERS_FIRST = No
    MERGED -> Tester_Pendulaires

Bookmark: 6. Choix des déplacements qui correspondent aux critères de paires de type origine et destinations (selon le tableau)
Tester_Pendulaires
    BOOL_OP = COMPOSITE
    COMPOSITE_TEST = ( 1 AND 2 ) OR ( 3 AND 4 )
    TEST_CLAUSE:
      TEST @Value(type_origine) = 1
      TEST @Value(type_destination) = 2
      TEST @Value(type_origine) = 2
      TEST @Value(type_destination) = 1
    TEST_MODE = TEST
    PASSED -> Tester_Motif
    FAILED -> Tester_Pendulaires_pro
Tester_Pendulaires_pro
    BOOL_OP = COMPOSITE
    COMPOSITE_TEST = ( 1 AND ( 2 OR 3 OR 4 )) OR (( 5 OR 6 OR 7 ) AND 8 )
    TEST_CLAUSE:
      TEST @Value(type_origine) = 1
      TEST @Value(type_destination) = 3
      TEST @Value(type_destination) = 4
      TEST @Value(type_destination) = 5
      TEST @Value(type_origine) = 3
      TEST @Value(type_origine) = 4
      TEST @Value(type_origine) = 5
      TEST @Value(type_destination) = 1
    TEST_MODE = TEST
    PASSED -> Tester_Motif_2
    FAILED -> Tester_Repas_pendulaires
Tester_Repas_pendulaires
    BOOL_OP = COMPOSITE
    COMPOSITE_TEST = ( 1 AND 2 ) OR ( 3 AND 4 )
    TEST_CLAUSE:
      TEST @Value(type_origine) = 2
      TEST @Value(type_destination) = 6
      TEST @Value(type_origine) = 6
      TEST @Value(type_destination) = 2
    TEST_MODE = TEST
    PASSED -> Tester_Motif_3
    FAILED -> Tester_Repas_pro
Tester_Repas_pro
    BOOL_OP = COMPOSITE
    COMPOSITE_TEST = (( 1 OR 2 OR 3 ) AND 4 ) OR ( 5 AND ( 6 OR 7 OR 8 ))
    TEST_CLAUSE:
      TEST @Value(type_origine) = 3
      TEST @Value(type_origine) = 4
      TEST @Value(type_origine) = 5
      TEST @Value(type_destination) = 6
      TEST @Value(type_origine) = 6
      TEST @Value(type_destination) = 3
      TEST @Value(type_destination) = 4
      TEST @Value(type_destination) = 5
    TEST_MODE = TEST
    PASSED -> Tester_Motif_5
    FAILED -> Tester_Professionnels
Tester_Professionnels
    BOOL_OP = COMPOSITE
    COMPOSITE_TEST = (( 1 OR 2 OR 3 ) AND ( 4 OR 5 OR 6 )) OR (( 7 OR 8 OR 9 ) AND 10 ) OR ( 11 AND ( 12 OR 13 OR 14 )) OR ( 15 AND 16 )
    TEST_CLAUSE:
      TEST @Value(type_origine) = 3
      TEST @Value(type_origine) = 4
      TEST @Value(type_origine) = 5
      TEST @Value(type_destination) = 3
      TEST @Value(type_destination) = 4
      TEST @Value(type_destination) = 5
      TEST @Value(type_origine) = 3
      TEST @Value(type_origine) = 4
      TEST @Value(type_origine) = 5
      TEST @Value(type_destination) = 2
      TEST @Value(type_origine) = 2
      TEST @Value(type_destination) = 3
      TEST @Value(type_destination) = 4
      TEST @Value(type_destination) = 5
      TEST @Value(type_origine) = 2
      TEST @Value(type_destination) = 2
    TEST_MODE = TEST
    PASSED -> Tester_Motif_4
    FAILED -> Junction_3
Note: Tester_Bureau-Bureau : Input
Junction_3
    -> Junction_4

Bookmark: 7. Choix des déplacements qui correspondent aux critères de motifs déclarés (selon le tableau)
Tester_Motif
    BOOL_OP = OR
    TEST_CLAUSE:
      TEST @Value(motif_id) = 8
      TEST @Value(motif_id) = 7
      TEST @Value(motif_id) = 11
      TEST @Value(motif_id) = 6
    TEST_MODE = TEST
    PASSED -> Sorter
    FAILED -> Junction_17
Note: FeatureMerger_15 : Requestor
Junction_17
    -> Junction_18
Tester_Motif_2
    BOOL_OP = OR
    TEST_CLAUSE:
      TEST @Value(motif_id) = 6
      TEST @Value(motif_id) = 7
      TEST @Value(motif_id) = 8
      TEST @Value(motif_id) = 11
    TEST_MODE = TEST
    PASSED -> Sorter
    FAILED -> Junction_15
Note: FeatureMerger_15 : Requestor
Junction_15
    -> Junction_16
Tester_Motif_3
    BOOL_OP = OR
    TEST_CLAUSE = TEST @Value(motif_id) = 11
    TEST_MODE = TEST
    PASSED -> Sorter
    FAILED -> Junction_13
Note: FeatureMerger_15 : Requestor
Junction_13
    -> Junction_14
Tester_Motif_5
    BOOL_OP = OR
    TEST_CLAUSE:
      TEST @Value(motif_id) = 11
      TEST @Value(motif_id) = 6
    TEST_MODE = TEST
    PASSED -> Sorter
    FAILED -> Junction_11
Note: FeatureMerger_15 : Requestor
Junction_11
    -> Junction_12
Tester_Motif_4
    BOOL_OP = OR
    TEST_CLAUSE:
      TEST @Value(motif_id) = 6
      TEST @Value(motif_id) = 11
    TEST_MODE = TEST
    PASSED -> Sorter
    FAILED -> Junction_9
Note: FeatureMerger_15 : Requestor
Junction_9
    -> Junction_10

Bookmark: Mise en avant des utilisateurs.trices avec déplacements rejetés (motifs jugés incohérents)
Note: Tester_Motif : Failed
Junction_18
    -> FeatureMerger_15 [REQUESTOR]
Note: Tester_Motif_2 : Failed
Junction_16
    -> FeatureMerger_15 [REQUESTOR]
Note: Tester_Motif_3 : Failed
Junction_14
    -> FeatureMerger_15 [REQUESTOR]
Note: Tester_Motif_5 : Failed
Junction_12
    -> FeatureMerger_15 [REQUESTOR]
Note: Tester_Motif_4 : Failed
Junction_10
    -> FeatureMerger_15 [REQUESTOR]
Note: FeatureMerger_utilisateurs.trices-profil : Merged
Junction_6
    -> FeatureMerger_15 [SUPPLIER]
Note: FeatureMerger_utilisateurs.trices-profil : UnmergedRequestor
Junction_8
    -> FeatureMerger_15 [SUPPLIER]
FeatureMerger_15
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    USED_SUPPLIER -> Utilisateurs.trices_avec_deplacements_rejetes
Utilisateurs.trices_avec_deplacements_rejetes: Inspector

Bookmark: Mise en avant des utilisateurs.trices avec déplacements rejetés (paires de type origine et destination, tests de certaines paires)
Note: Tester_Professionnels : Failed
Junction_4
    -> Tester_Bureau-Bureau
Tester_Bureau-Bureau
    BOOL_OP = COMPOSITE
    COMPOSITE_TEST = 1 AND 2
    TEST_CLAUSE:
      TEST @Value(type_origine) = 2
      TEST @Value(type_destination) = 2
    TEST_MODE = TEST
    PASSED -> FeatureMerger_35 [REQUESTOR]
    FAILED -> Tester_Domicile-Domicile
Tester_Domicile-Domicile
    BOOL_OP = COMPOSITE
    COMPOSITE_TEST = 1 AND 2
    TEST_CLAUSE:
      TEST @Value(type_origine) = 1
      TEST @Value(type_destination) = 1
    TEST_MODE = TEST
    PASSED -> FeatureMerger_36 [REQUESTOR]
    FAILED -> FeatureMerger_utilisateurs.trices_avec_autres_paires [REQUESTOR]
Note: FeatureMerger_utilisateurs.trices-profil : Merged
Junction_48
    -> FeatureMerger_utilisateurs.trices_avec_autres_paires [SUPPLIER]
Note: FeatureMerger_utilisateurs.trices-profil : UnmergedRequestor
Junction_46
    -> FeatureMerger_utilisateurs.trices_avec_autres_paires [SUPPLIER]
FeatureMerger_utilisateurs.trices_avec_autres_paires
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    MERGED -> Junction
    USED_SUPPLIER -> Utilisateurs.trices_avec_deplacements_rejetes_2
Note: Sorter : Input
Junction
    -> Junction_2
Utilisateurs.trices_avec_deplacements_rejetes_2: Inspector
Note: FeatureMerger_utilisateurs.trices-profil : Merged
Junction_52
    -> FeatureMerger_35 [SUPPLIER]
Note: FeatureMerger_utilisateurs.trices-profil : UnmergedRequestor
Junction_42
    -> FeatureMerger_35 [SUPPLIER]
FeatureMerger_35
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    USED_SUPPLIER -> Utilisateurs.trices_avec_deplacements_rejetes_6
Utilisateurs.trices_avec_deplacements_rejetes_6: Inspector
Note: FeatureMerger_utilisateurs.trices-profil : UnmergedRequestor
Junction_50
    -> FeatureMerger_36 [SUPPLIER]
Note: FeatureMerger_utilisateurs.trices-profil : Merged
Junction_44
    -> FeatureMerger_36 [SUPPLIER]
FeatureMerger_36
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    USED_SUPPLIER -> Utilisateurs.trices_avec_deplacements_rejetes_5
Utilisateurs.trices_avec_deplacements_rejetes_5: Inspector

Bookmark: Traitement des utilisateurs.trices
auth_user (reader POSTGRES_1)
    attributes: id serial,PrimaryKey, password varchar(128), last_login timestamptz, is_superuser bool, username varchar(150),Unique, first_name varchar(150), last_name varchar(150), email varchar(254), is_staff bool, is_active bool, date_joined timestamptz
    -> AttributeKeeper_2
AttributeKeeper_2
    CREATE_BULK_MODE_FEATURES = NO
    KEEP_ATTRS = id,username
    -> Tester
Tester
    BOOL_OP = COMPOSITE
    COMPOSITE_TEST = 1 AND 2 AND 3 AND 4
    TEST_CLAUSE:
      TEST @Value(username) NOT_= mathieua
      TEST @Value(username) NOT_= delacretaz
      TEST @Value(username) NOT_= ingensand
      TEST @Value(username) NOT_= manoni
    TEST_MODE = TEST
    PASSED -> FeatureMerger_utilisateurs.trices-profil [REQUESTOR]

Bookmark: Mise en avant des utilisateurs.trices avec déplacements rejetés (déplacements non inversés)
Note: FeatureMerger_utilisateurs.trices-profil : UnmergedRequestor
Junction_26
    -> FeatureMerger_16 [SUPPLIER]
Note: FeatureMerger_utilisateurs.trices-profil : Merged
Junction_28
    -> FeatureMerger_16 [SUPPLIER]
Note: Tester_2 : Passed
Junction_30
    -> FeatureMerger_16 [REQUESTOR]
FeatureMerger_16
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    USED_SUPPLIER -> Utilisateurs.trices_avec_deplacements_rejetes_7
Utilisateurs.trices_avec_deplacements_rejetes_7: Inspector

Bookmark: Mise en avant des utilisateurs.trices avec déplacements rejetés (déplacements ne se suivent pas)
Note: FeatureMerger_utilisateurs.trices-profil : UnmergedRequestor
Junction_36
    -> FeatureMerger_24 [SUPPLIER]
Note: FeatureMerger_utilisateurs.trices-profil : Merged
Junction_32
    -> FeatureMerger_24 [SUPPLIER]
Note: FeatureMerger_3 : UnmergedRequestor
Junction_40
    -> FeatureMerger_24 [REQUESTOR]
FeatureMerger_24
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    USED_SUPPLIER -> Utilisateurs.trices_avec_deplacements_rejetes_4
Utilisateurs.trices_avec_deplacements_rejetes_4: Inspector

Bookmark: 8. Contrôle que le départ d'un déplacement correspond à l'arrivée du déplacement précédent durant une journée
Note: FeatureMerger_utilisateurs.trices_avec_autres_paires : Merged (après nettoyage et contrôle)
Junction_2
    -> Sorter
Sorter
    SORT_PARM = utilisateur_id NATURAL ASCENDING date NATURAL ASCENDING heure_depart NATURAL ASCENDING
    SORTED -> StatisticsCalculator
StatisticsCalculator
    CALCULATION_MODE = NUMERIC
    FEAT_STATS = id_deplacement,NUMERIC_MODE,,,COUNT,,,,,,,,,,
    GROUP_BY = utilisateur_id date
    COMPLETE -> Tester_3
Tester_3
    BOOL_OP = OR
    TEST_CLAUSE = TEST @Value(id_deplacement.total_count) > 1
    TEST_MODE = TEST
    PASSED -> Aggregator
    PASSED -> FeatureMerger_3 [REQUESTOR]
    FAILED -> Junction_19
Aggregator
    ACCUM_ATTRS_NAME = Merge Incoming Attributes
    CONCAT_ATTRS = lieu_arrivee_id lieu_depart_id
    GROUP_BY = date utilisateur_id
    MODE = Attributes Only
    SEP = ,
    AGGREGATE -> AttributeSplitter
AttributeSplitter
    ATTR_NAME = lieu_depart_id
    DELIMITER = ,
    DROP_EMPTY_PARTS = No
    LIST_NAME = lieu_depart_id
    TRIM_OPTION = Both
    -> AttributeSplitter_2
AttributeSplitter_2
    ATTR_NAME = lieu_arrivee_id
    DELIMITER = ,
    DROP_EMPTY_PARTS = No
    LIST_NAME = lieu_arrivee_id
    TRIM_OPTION = Both
    -> AttributeManager_4
AttributeManager_4
    ATTR_TABLE:
      SET_TO trajet = 1
      SET_TO arrivee = @Value(trajet)
      SET_TO depart = @Evaluate(@Value(trajet)-1)
    USER_EXPOSED_ATTRIBUTES = x_origine,y_origine,x_destination,y_destination
    -> test [Tester_2_Input]
test
    ARRIVEE = @Value(arrivee)
    DATE = @Value(date)
    DEPART = @Value(depart)
    HEURE_ARRIVEE = @Value(heure_arrivee)
    HEURE_DEPART = @Value(heure_depart)
    ID_DEPLACEMENT = @Value(id_deplacement)
    ID_DEPLACEMENT.TOTAL_COUNT = @Value(id_deplacement.total_count)
    LIEU_ARRIVEE_ID = @Value(lieu_arrivee_id)
    LIEU_DEPART_ID = @Value(lieu_depart_id)
    MODE_ID = @Value(mode_id)
    MOTIF_ID = @Value(motif_id)
    RAISON_ID = @Value(raison_id)
    TRAJET = @Value(trajet)
    UTILISATEUR_ID = @Value(utilisateur_id)
    OK -> AttributeKeeper
    PROBLEME_2 -> ListSummer
ListSummer
    RESULT = _sum_arrivee
    SRC_LIST = lieu_arrivee_id{}
    -> ListSummer_2
ListSummer_2
    RESULT = _sum_depart
    SRC_LIST = lieu_depart_id{}
    -> Tester_2
Tester_2
    BOOL_OP = COMPOSITE
    COMPOSITE_TEST = 1 AND 2 AND 3
    TEST_CLAUSE:
      TEST @Value(lieu_depart_id{0}) = @Evaluate(@Value(_sum_depart)/@Value(id_deplacement.total_count))
      TEST @Value(lieu_arrivee_id{0}) = @Evaluate(@Value(_sum_arrivee)/@Value(id_deplacement.total_count))
      TEST @Value(lieu_depart_id{0}) != @Value(lieu_arrivee_id{0})
    TEST_MODE = TEST
    PASSED -> Junction_29
Note: FeatureMerger_16 : Requestor
Junction_29
    -> Junction_30
AttributeKeeper
    CREATE_BULK_MODE_FEATURES = NO
    KEEP_ATTRS = date,utilisateur_id
    -> FeatureMerger_3 [SUPPLIER]
FeatureMerger_3
    ATTR_ACCUM_MODE = Merge Supplier
    ATTR_CONFLICT_RES = Use Requestor
    IGNORE_NULLS = No
    JOIN_KEYS = @Value(utilisateur_id) @Value(utilisateur_id) AUTO @Value(date) @Value(date) AUTO
    MERGE_TYPE = Attributes Only
    PROCESS_DUPS = NO
    REJECT_NULL_MISSING_KEYS = No
    SUPPLIERS_FIRST = No
    MERGED -> FeatureMerger_deplacements-utilisateurs.trices [REQUESTOR]
    UNMERGED_REQUESTOR -> Junction_39
Note: FeatureMerger_24 : Requestor
Junction_39
    -> Junction_40
Note: FeatureMerger_37 : Requestor
Junction_19
    -> Junction_20

Bookmark: Mise en avant des utilisateurs.trices avec déplacements rejetés (1 seul trajet dans une journée)
Note: Tester_3 : Failed
Junction_20
    -> FeatureMerger_37 [REQUESTOR]
Note: FeatureMerger_utilisateurs.trices-profil : UnmergedRequestor
Junction_24
    -> FeatureMerger_37 [SUPPLIER]
Note: FeatureMerger_utilisateurs.trices-profil : Merged
Junction_22
    -> FeatureMerger_37 [SUPPLIER]
FeatureMerger_37
    ATTR_ACCUM_MODE = Merge Supplier
    ATTR_CONFLICT_RES = Use Requestor
    IGNORE_NULLS = No
    JOIN_KEYS = @Value(utilisateur_id) @Value(id) AUTO
    MERGE_TYPE = Attributes Only
    PROCESS_DUPS = NO
    REJECT_NULL_MISSING_KEYS = No
    SUPPLIERS_FIRST = No
    USED_SUPPLIER -> Utilisateurs.trices_avec_deplacements_rejetes_3
Utilisateurs.trices_avec_deplacements_rejetes_3: Inspector

Bookmark: 9. Contrôle du nombre de jours remplis par l'utilisateur.trice
Note: Par utilisateur.trice et par jour
StatisticsCalculator_nb_deplacement
    CALCULATION_MODE = NUMERIC
    FEAT_STATS = id_deplacement,NUMERIC_MODE,,,COUNT,,,,,,,,,,
    GROUP_BY = date username
    SUMMARY -> StatisticsCalculator_nb_jours_avec_deplacements
StatisticsCalculator_nb_jours_avec_deplacements
    CALCULATION_MODE = NUMERIC
    FEAT_STATS = date,NUMERIC_MODE,,,COUNT,,,,,,,,,,
    GROUP_BY = username
    SUMMARY -> AttributeManager_29
AttributeManager_29
    ATTR_TABLE:
      RENAME_SET_VALUE date.total_count > nb_jours_avec_deplacements
      SET_TO nb_jours_sans_deplacements = @Evaluate(10-@Value(nb_jours_avec_deplacements))
    -> Tester_nb_jours_sans_deplacements
Tester_nb_jours_sans_deplacements
    BOOL_OP = OR
    TEST_CLAUSE = TEST @Value(nb_jours_sans_deplacements) > 5
    TEST_MODE = TEST
    PASSED -> Utilisateurs.trices_avec_plus_de_5_jours_sans_deplacements
Utilisateurs.trices_avec_plus_de_5_jours_sans_deplacements: Inspector

FME custom transformer test

Parameters:
- DATE = @Value(date)   # date
- MOTIF_ID = @Value(motif_id)   # Motif Id
- HEURE_DEPART = @Value(heure_depart)   # Heure Depart
- DEPART = @Value(depart)   # depart
- LIEU_DEPART_ID = @Value(lieu_depart_id)   # Lieu Depart Id
- ID_DEPLACEMENT = @Value(id_deplacement)   # Id Deplacement
- ARRIVEE = @Value(arrivee)   # arrivee
- MODE_ID = @Value(mode_id)   # Mode Id
- UTILISATEUR_ID = @Value(utilisateur_id)   # Utilisateur Id
- RAISON_ID = @Value(raison_id)   # Raison Id
- ID_DEPLACEMENT.TOTAL_COUNT = @Value(id_deplacement.total_count)   # Id Deplacement.total Count
- LIEU_ARRIVEE_ID = @Value(lieu_arrivee_id)   # Lieu Arrivee Id
- HEURE_ARRIVEE = @Value(heure_arrivee)   # Heure Arrivee
- TRAJET = @Value(trajet)   # trajet

Tester_2_Input (input)
    -> Tester_2
Tester_2
    BOOL_OP = OR
    TEST_CLAUSE = TEST @Value(lieu_arrivee_id{@Value(depart)}) = @Value(lieu_depart_id{@Value(arrivee)})
    TEST_MODE = TEST
    PASSED -> AttributeManager_3
    FAILED -> PROBLEME_2 (output)
AttributeManager_3
    ATTR_TABLE = SET_TO trajet = @Evaluate(@Value(trajet)+1)
    USER_EXPOSED_ATTRIBUTES = _count
    -> AttributeManager_2
AttributeManager_2
    ATTR_TABLE:
      SET_TO arrivee = @Value(trajet)
      SET_TO depart = @Evaluate(@Value(trajet)-1)
    USER_EXPOSED_ATTRIBUTES = _count
    -> Tester_4
Tester_4
    BOOL_OP = OR
    TEST_CLAUSE = TEST @Value(trajet) = @Value(id_deplacement.total_count)
    TEST_MODE = TEST
    PASSED -> OK (output)
    FAILED -> Tester_2_Input (output)
OK (output)
Tester_2_Input (output)
PROBLEME_2 (output)
