FME workspace 3_calculs_API_ORS.fmw

Parameters:
- DestDataset_XLSXW = $(FME_MF_DIR)distance_et_temps_parcours_voiture.xlsx   # Destination Microsoft Excel File
- SourceDataset_XLSXR = $(FME_MF_DIR)coord_deplacements.xlsx   # Source Microsoft Excel File(s)

Readers:
- XLSXR_1: XLSXR from $(SourceDataset_XLSXR)

Writers:
- XLSXW_1: XLSXW to $(DestDataset_XLSXW)

coord_deplacements (reader XLSXR_1)
    attributes: id_deplacement number(5,0), x_destination number(16,14), y_destination number(16,13), x_origine x_coordinate, y_origine y_coordinate
    -> AttributeManager_7
    -> AttributeManager_2
    -> AttributeManager_5
AttributeManager_7
    ATTR_TABLE:
      SET_TO coord_trajet = @Value(x_origine),@Value(y_origine);@Value(x_destination),@Value(y_destination)
      SET_TO coord_origine = @Value(x_origine),@Value(y_origine)
      SET_TO coord_destination = @Value(x_destination),@Value(y_destination)
    USER_EXPOSED_ATTRIBUTES = id_deplacement.total_count
    -> Decelerator
Decelerator
    DECEL_TYPE = Limit Features Per Second
    FEATURES_PER_SECOND = 35/60
    -> HTTPCaller_API_ORS
FeatureMerger_3
    ATTR_ACCUM_MODE = Merge Supplier
    ATTR_CONFLICT_RES = Use Requestor
    IGNORE_NULLS = No
    JOIN_KEYS = @Value(id_deplacement) @Value(id_deplacement) AUTO
    MERGE_TYPE = Attributes Only
    PROCESS_DUPS = NO
    REJECT_NULL_MISSING_KEYS = No
    SUPPLIERS_FIRST = No
    MERGED -> AttributeKeeper
AttributeKeeper
    CREATE_BULK_MODE_FEATURES = NO
    KEEP_ATTRS = distance_voiture_km,id_deplacement,temps_parcours_voiture_min
    -> voiture (writer XLSXW_1)
voiture (writer XLSXW_1)
    attributes: id_deplacement number(5), distance_voiture_km string(200), temps_parcours_voiture_min string(200)
AttributeManager_2
    ATTR_TABLE:
      SET_TO coord_trajet = @Value(x_origine),@Value(y_origine);@Value(x_destination),@Value(y_destination)
      SET_TO coord_origine = @Value(x_origine),@Value(y_origine)
      SET_TO coord_destination = @Value(x_destination),@Value(y_destination)
    USER_EXPOSED_ATTRIBUTES = id_deplacement.total_count
    -> Decelerator_2
Decelerator_2
    DECEL_TYPE = Limit Features Per Second
    FEATURES_PER_SECOND = 35/60
    -> HTTPCaller_API_ORS_2
FeatureMerger_2
    ATTR_ACCUM_MODE = Merge Supplier
    ATTR_CONFLICT_RES = Use Requestor
    IGNORE_NULLS = No
    JOIN_KEYS = @Value(id_deplacement) @Value(id_deplacement) AUTO
    MERGE_TYPE = Attributes Only
    PROCESS_DUPS = NO
    REJECT_NULL_MISSING_KEYS = No
    SUPPLIERS_FIRST = No
    MERGED -> AttributeKeeper_2
AttributeKeeper_2
    CREATE_BULK_MODE_FEATURES = NO
    KEEP_ATTRS = id_deplacement,distance_velo_km,temps_parcours_velo_min
    -> velo (writer XLSXW_1)
velo (writer XLSXW_1)
    attributes: id_deplacement number(5), distance_velo_km string(200), temps_parcours_velo_min string(200)
AttributeManager_5
    ATTR_TABLE:
      SET_TO coord_trajet = @Value(x_origine),@Value(y_origine);@Value(x_destination),@Value(y_destination)
      SET_TO coord_origine = @Value(x_origine),@Value(y_origine)
      SET_TO coord_destination = @Value(x_destination),@Value(y_destination)
    USER_EXPOSED_ATTRIBUTES = id_deplacement.total_count
    -> Decelerator_3
Decelerator_3
    DECEL_TYPE = Limit Features Per Second
    FEATURES_PER_SECOND = 35/60
    -> HTTPCaller_API_ORS_3
FeatureMerger_4
    ATTR_ACCUM_MODE = Merge Supplier
    ATTR_CONFLICT_RES = Use Requestor
    IGNORE_NULLS = No
    JOIN_KEYS = @Value(id_deplacement) @Value(id_deplacement) AUTO
    MERGE_TYPE = Attributes Only
    PROCESS_DUPS = NO
    REJECT_NULL_MISSING_KEYS = No
    SUPPLIERS_FIRST = No
    MERGED -> AttributeKeeper_3
AttributeKeeper_3
    CREATE_BULK_MODE_FEATURES = NO
    KEEP_ATTRS = id_deplacement,distance_marche_km,temps_parcours_marche_min
    -> marche (writer XLSXW_1)
marche (writer XLSXW_1)
    attributes: id_deplacement number(5), distance_marche_km string(200), temps_parcours_marche_min string(200)

Bookmark: Calcul distance et temps de parcours en voiture avec API ORS
HTTPCaller_API_ORS
    ADDITIONAL_URL_PARAMETERS = start;@Value(coord_origine) end;@Value(coord_destination)
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.openrouteservice.org/v2/directions/driving-car?api_key=
    TRANSFER_TIMEOUT_LENGTH = 90
    USE_COOKIES = No
    VERIFY_SSL_CERTIFICATES = Yes
    -> StringSearcher_3
    -> StringSearcher_4
StringSearcher_3
    CASE = no
    MATCHED_RESULT_ATTR = _first_match
    REGEXP = "distance":([0-9]*)
    STRING_TO_SEARCH = @Value(_response_body)
    MATCHED -> AttributeSplitter_7
AttributeSplitter_7
    ATTR_NAME = _first_match
    DELIMITER = :
    DROP_EMPTY_PARTS = No
    LIST_NAME = distance
    TRIM_OPTION = Both
    -> AttributeManager_6
AttributeManager_6
    ATTR_TABLE = SET_TO distance_voiture_km = @Evaluate(@round(@Value(distance{1})/1000,2))
    -> FeatureMerger_3 [REQUESTOR]
StringSearcher_4
    CASE = no
    MATCHED_RESULT_ATTR = _first_match
    REGEXP = "duration":([0-9]*)
    STRING_TO_SEARCH = @Value(_response_body)
    MATCHED -> AttributeSplitter_8
AttributeSplitter_8
    ATTR_NAME = _first_match
    DELIMITER = :
    DROP_EMPTY_PARTS = No
    LIST_NAME = duration
    TRIM_OPTION = Both
    -> AttributeManager_9
AttributeManager_9
    ATTR_TABLE = SET_TO temps_parcours_voiture_min = @Evaluate(@round(@Value(duration{1})/60,0))
    USER_EXPOSED_ATTRIBUTES = id_deplacement.total_count
    -> FeatureMerger_3 [SUPPLIER]

Bookmark: Calcul distance et temps de parcours en vélo avec API ORS
HTTPCaller_API_ORS_2
    ADDITIONAL_URL_PARAMETERS = start;@Value(coord_origine) end;@Value(coord_destination)
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.openrouteservice.org/v2/directions/cycling-regular?api_key=
    TRANSFER_TIMEOUT_LENGTH = 90
    USE_COOKIES = No
    VERIFY_SSL_CERTIFICATES = Yes
    -> StringSearcher_2
    -> StringSearcher_5
StringSearcher_2
    CASE = no
    MATCHED_RESULT_ATTR = _first_match
    REGEXP = "distance":([0-9]*)
    STRING_TO_SEARCH = @Value(_response_body)
    MATCHED -> AttributeSplitter_2
AttributeSplitter_2
    ATTR_NAME = _first_match
    DELIMITER = :
    DROP_EMPTY_PARTS = No
    LIST_NAME = distance
    TRIM_OPTION = Both
    -> AttributeManager_3
AttributeManager_3
    ATTR_TABLE = SET_TO distance_velo_km = @Evaluate(@round(@Value(distance{1})/1000,2))
    -> FeatureMerger_2 [REQUESTOR]
StringSearcher_5
    CASE = no
    MATCHED_RESULT_ATTR = _first_match
    REGEXP = "duration":([0-9]*)
    STRING_TO_SEARCH = @Value(_response_body)
    MATCHED -> AttributeSplitter_3
AttributeSplitter_3
    ATTR_NAME = _first_match
    DELIMITER = :
    DROP_EMPTY_PARTS = No
    LIST_NAME = duration
    TRIM_OPTION = Both
    -> AttributeManager_4
AttributeManager_4
    ATTR_TABLE = SET_TO temps_parcours_velo_min = @Evaluate(@round(@Value(duration{1})/60,0))
    USER_EXPOSED_ATTRIBUTES = id_deplacement.total_count
    -> FeatureMerger_2 [SUPPLIER]

Bookmark: Calcul distance et temps de parcours à pied avec API ORS
HTTPCaller_API_ORS_3
    ADDITIONAL_URL_PARAMETERS = start;@Value(coord_origine) end;@Value(coord_destination)
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.openrouteservice.org/v2/directions/foot-walking?api_key=
    TRANSFER_TIMEOUT_LENGTH = 90
    USE_COOKIES = No
    VERIFY_SSL_CERTIFICATES = Yes
    -> StringSearcher_6
    -> StringSearcher_7
StringSearcher_6
    CASE = no
    MATCHED_RESULT_ATTR = _first_match
    REGEXP = "distance":([0-9]*)
    STRING_TO_SEARCH = @Value(_response_body)
    MATCHED -> AttributeSplitter_4
AttributeSplitter_4
    ATTR_NAME = _first_match
    DELIMITER = :
    DROP_EMPTY_PARTS = No
    LIST_NAME = distance
    TRIM_OPTION = Both
    -> AttributeManager_8
AttributeManager_8
    ATTR_TABLE = SET_TO distance_marche_km = @Evaluate(@round(@Value(distance{1})/1000,2))
    -> FeatureMerger_4 [REQUESTOR]
StringSearcher_7
    CASE = no
    MATCHED_RESULT_ATTR = _first_match
    REGEXP = "duration":([0-9]*)
    STRING_TO_SEARCH = @Value(_response_body)
    MATCHED -> AttributeSplitter_5
AttributeSplitter_5
    ATTR_NAME = _first_match
    DELIMITER = :
    DROP_EMPTY_PARTS = No
    LIST_NAME = duration
    TRIM_OPTION = Both
    -> AttributeManager_10
AttributeManager_10
    ATTR_TABLE = SET_TO temps_parcours_marche_min = @Evaluate(@round(@Value(duration{1})/60,0))
    USER_EXPOSED_ATTRIBUTES = id_deplacement.total_count
    -> FeatureMerger_4 [SUPPLIER]
