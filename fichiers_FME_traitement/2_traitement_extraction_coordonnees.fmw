FME workspace 2_traitement_extraction_coordonnees.fmw

Parameters:
- SourceDataset_POSTGIS = portail_gdb   # Connection
- SourceDataset_POSTGRES = portail_gdb   # Connection
- DestDataset_XLSXW_7 = $(FME_MF_DIR)coord_deplacements.xlsx   # Destination Microsoft Excel File
- DestDataset_XLSXW_8 = $(FME_MF_DIR)coord_deplacements_TP.xlsx   # Destination Microsoft Excel File

Readers:
- POSTGIS_1: POSTGIS from $(SourceDataset_POSTGIS)
- POSTGRES_1: POSTGRES from $(SourceDataset_POSTGRES)

Writers:
- XLSXW_3: XLSXW to $(DestDataset_XLSXW_7)
- XLSXW_5: XLSXW to $(DestDataset_XLSXW_8)

Bookmark: Gestion des clés étrangères des déplacements
deplacements_deplacement (reader POSTGRES_1)
    attributes: id_deplacement serial,PrimaryKey, date date, heure_depart time, heure_arrivee time, lieu_arrivee_id int4,BTREE, lieu_depart_id int4,BTREE, mode_id int4,BTREE, motif_id int4,BTREE, raison_id int4,BTREE, utilisateur_id int4,BTREE
    -> FeatureMerger_6 [REQUESTOR]
deplacements_mode (reader POSTGRES_1)
    attributes: id_mode serial,PrimaryKey, nom_mode varchar(100), alias_mode varchar(100)
    -> FeatureMerger_6 [SUPPLIER]
FeatureMerger_6
    ATTR_ACCUM_MODE = Merge Supplier
    ATTR_CONFLICT_RES = Use Requestor
    IGNORE_NULLS = No
    JOIN_KEYS = @Value(mode_id) @Value(id_mode) AUTO
    MERGE_TYPE = Attributes Only
    PROCESS_DUPS = NO
    REJECT_NULL_MISSING_KEYS = No
    SUPPLIERS_FIRST = No
    MERGED -> FeatureMerger_7 [REQUESTOR]
deplacements_motif (reader POSTGRES_1)
    attributes: id_motif serial,PrimaryKey, nom_motif varchar(150), alias_motif varchar(100)
    -> FeatureMerger_7 [SUPPLIER]
FeatureMerger_7
    ATTR_ACCUM_MODE = Merge Supplier
    ATTR_CONFLICT_RES = Use Requestor
    IGNORE_NULLS = No
    JOIN_KEYS = @Value(motif_id) @Value(id_motif) AUTO
    MERGE_TYPE = Attributes Only
    PROCESS_DUPS = NO
    REJECT_NULL_MISSING_KEYS = No
    SUPPLIERS_FIRST = No
    MERGED -> FeatureMerger_8 [REQUESTOR]
deplacements_raison (reader POSTGRES_1)
    attributes: id_raison serial,PrimaryKey, nom_raison varchar(100), alias_raison varchar(100)
    -> FeatureMerger_8 [SUPPLIER]
FeatureMerger_8
    ATTR_ACCUM_MODE = Merge Supplier
    ATTR_CONFLICT_RES = Use Requestor
    IGNORE_NULLS = No
    JOIN_KEYS = @Value(raison_id) @Value(id_raison) AUTO
    MERGE_TYPE = Attributes Only
    PROCESS_DUPS = NO
    REJECT_NULL_MISSING_KEYS = No
    SUPPLIERS_FIRST = No
    MERGED -> AttributeManager_14
AttributeManager_14
    ATTR_TABLE:
      REMOVE id_mode
      REMOVE id_motif
      REMOVE id_raison
    -> FeatureMerger [REQUESTOR]

Bookmark: Gestion des clés étrangères des lieux
deplacements_lieu (reader POSTGIS_1)
    attributes: id serial,PrimaryKey, nom varchar(100), rue varchar(100), no_entree varchar(10), npa int4, localite varchar(50), utilisateur_id int4,BTREE, type_id int4,BTREE
    -> AttributeManager_3
AttributeManager_3
    ATTR_TABLE = RENAME_SET_VALUE id > id_lieu
    -> FeatureMerger_9 [REQUESTOR]
deplacements_type (reader POSTGRES_1)
    attributes: id_type serial,PrimaryKey, nom_type varchar(100), alias_type varchar(100)
    -> FeatureMerger_9 [SUPPLIER]
FeatureMerger_9
    ATTR_ACCUM_MODE = Merge Supplier
    ATTR_CONFLICT_RES = Use Requestor
    IGNORE_NULLS = No
    JOIN_KEYS = @Value(type_id) @Value(id_type) AUTO
    MERGE_TYPE = Attributes and Geometry
    PROCESS_DUPS = NO
    REJECT_NULL_MISSING_KEYS = No
    SUPPLIERS_FIRST = No
    MERGED -> AttributeManager_2

Bookmark: Ajout attributs: coordonnées origine et destination
AttributeManager_2
    ATTR_TABLE:
      REMOVE rue
      REMOVE no_entree
      REMOVE npa
      REMOVE localite
      RENAME_SET_VALUE type_id
    USER_EXPOSED_ATTRIBUTES = id
    -> CoordinateExtractor_2
    -> FeatureMerger [REQUESTOR]
    -> CoordinateExtractor
CoordinateExtractor
    IND = 0
    MODE = Specify Coordinate
    X_ATTR = x_origine
    Y_ATTR = y_origine
    -> FeatureMerger [SUPPLIER]
FeatureMerger
    ATTR_ACCUM_MODE = Merge Supplier
    ATTR_CONFLICT_RES = Use Requestor
    IGNORE_NULLS = No
    JOIN_KEYS = @Value(lieu_depart_id) @Value(id_lieu) AUTO
    MERGE_TYPE = Attributes and Geometry
    PROCESS_DUPS = NO
    REJECT_NULL_MISSING_KEYS = No
    SUPPLIERS_FIRST = No
    MERGED -> FeatureMerger_2 [REQUESTOR]
CoordinateExtractor_2
    IND = 0
    MODE = Specify Coordinate
    X_ATTR = x_destination
    Y_ATTR = y_destination
    -> FeatureMerger_2 [SUPPLIER]
FeatureMerger_2
    ATTR_ACCUM_MODE = Merge Supplier
    ATTR_CONFLICT_RES = Use Requestor
    IGNORE_NULLS = No
    JOIN_KEYS = @Value(lieu_arrivee_id) @Value(id_lieu) AUTO
    MERGE_TYPE = Attributes Only
    PROCESS_DUPS = NO
    REJECT_NULL_MISSING_KEYS = No
    SUPPLIERS_FIRST = No
    MERGED -> AttributeKeeper_3
    MERGED -> AttributeKeeper_4

Bookmark: Sortie des coord. origine-destination pour calcul des distances avec API ORS
AttributeKeeper_3
    CREATE_BULK_MODE_FEATURES = NO
    KEEP_ATTRS = id_deplacement,x_destination,x_origine,y_destination,y_origine
    -> coord_deplacements (writer XLSXW_3)
coord_deplacements (writer XLSXW_3)
    attributes: id_deplacement number(20), x_origine number(20), y_origine number(20), x_destination number(20), y_destination number(20)

Bookmark: Sortie des coord. origine-destination, date, heure_depart pour calcul des distances avec API Transport
AttributeKeeper_4
    CREATE_BULK_MODE_FEATURES = NO
    KEEP_ATTRS = id_deplacement,x_destination,x_origine,y_destination,y_origine,date,heure_depart,nom_mode
    -> Tester_8
Tester_8
    BOOL_OP = OR
    TEST_CLAUSE:
      TEST @Value(nom_mode) = Autopartage (Mobility)
      TEST @Value(nom_mode) = Co-voiturage
      TEST @Value(nom_mode) = Scooter, moto thermique
      TEST @Value(nom_mode) = Voiture d’entreprise collective électrique (y compris Twizy)
      TEST @Value(nom_mode) = Voiture d’entreprise collective thermique
      TEST @Value(nom_mode) = Voiture de fonction individuelle thermique
      TEST @Value(nom_mode) = Voiture privée/personnelle électrique
      TEST @Value(nom_mode) = Voiture privée/personnelle thermique
    TEST_MODE = TEST
    PASSED -> coord_deplacements_TP (writer XLSXW_5)
coord_deplacements_TP (writer XLSXW_5)
    attributes: id_deplacement number(20), date date(20), heure_depart time(20), nom_mode string(100), x_origine number(20), y_origine number(20), x_destination number(20), y_destination number(20)
